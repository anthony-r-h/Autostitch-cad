;;; Stitched banner with flow inside YOU and a diamond background.
;;; Load examples/demo.lsp, then ASTBANNERDEMO.
(defun ast:banner-settings ()
  (ast:cad-put 'pitch 2.7 (ast:cad-default-settings)))
(defun ast:banner-configure (guides / guide result)
  (foreach guide guides
    (setq result (ast:cad-save-inputs guide (ast:banner-settings) nil))
    (ast:cad-require (ast:cad-get 'ok result) (ast:cad-get 'error result))))
(defun ast:banner-script (letter scale / tail rise crossing ux uy)
  (cond
    ((= letter "c") (list (ast:show-stroke
      '((20.48528137424 20.48528137424 2.414213562373095)
        (20.48528137424 3.51471862576) (27.88528137424 10.91471862576)) nil)))
    ((= letter "a")
      ;; A true circle and a separate upright: no cusp or crossing through the bowl.
      (list (ast:show-stroke '((24 12 1.0) (0 12 1.0)) T)
        (ast:show-stroke '((26.4 24) (26.4 6 1.0) (34.2 6)) nil)))
    ((= letter "n") (list
      (ast:show-stroke '((0 0) (0 15 -1.0) (18 15) (18 5.357142857142857 1.0) (30 5.357142857142857)) nil)))
    ((= letter "r") (list
      (ast:show-stroke '((0 0) (0 15 -1.0) (18 15)) nil)))
    ((= letter "e") (list
      (ast:show-stroke '((2.9 12) (18 12 1.0) (0 12) (0 6 1.0) (18 6)) nil)))
    ((= letter "l")
      ;; Start at the loop junction; omit the low entry stroke that crowds the previous letter.
      (setq rise (sqrt (+ (expt 17.41287932795540 2.0) (expt 36.41142174524449 2.0)))
        ux (/ 17.41287932795540 rise) uy (/ 36.41142174524449 rise)
        crossing (* 6.0 (/ uy ux)) tail (- crossing (/ 6.75 scale)))
      (list
        (ast:show-stroke (list (list 0 crossing)
          '(11.41287932795540 36.41142174524449)) nil)
        (ast:show-stroke (list '(11.41287932795540 36.41142174524449 1.252211308703801)
          '(0 39) (list 0 tail 1.0) (list 12 tail)) nil)))
    ((= letter "y") (list
      (ast:show-stroke '((0 24) (0 9 0.414213562373095) (8.9 0.1) (18 12.2)) nil)
      (ast:show-stroke (list (list 18 (+ 12.2 (/ 9.45 scale))) '(18 -9 -1.0)
        '(0 -9) (list 0 (+ -9.0 (/ 2.7 scale)))) nil)))
    ((= letter "?") (list
      (ast:show-stroke '((0 30 -2.414213562373095) (10 20) (10 11.5)) nil)
      (ast:show-stroke '((8.5 3 1.0) (11.5 3 1.0)) T)))))

(defun ast:banner-outline (letter)
  (cond
    ((= letter "Y") (list (ast:show-stroke
      '((0 70) (19 70) (25 54.2) (31 70) (50 70) (35 36) (35 0) (15 0) (15 36)) T)))
    ((= letter "O") (list
      (ast:show-stroke '((0 0) (44 0) (44 70) (0 70)) T)
      (ast:show-stroke '((16 16) (28 16) (28 54) (16 54)) T)))
    ((= letter "U") (list (ast:show-stroke
      '((0 70) (0 22 1.0) (44 22) (44 70) (28 70) (28 22 -1.0) (16 22) (16 70)) T)))))

(setq ast:banner-lettering-layout
  '(("can" 0.84 -12.0 (("c" 0.0) ("a" 30.0) ("n" 65.0)))
    ("YOU" 1.0 0.0 (("Y" 0.0) ("O" 56.0) ("U" 106.0)))
    ("really?" 0.84 -12.0
      (("r" 0.0) ("e" 20.0) ("a" 42.0) ("l" 78.0) ("l" 96.0) ("y" 114.0) ("?" 134.0)))))

(defun ast:banner-poly (stroke origin layer / data point)
  (setq data (list '(0 . "LWPOLYLINE") '(100 . "AcDbEntity") (cons 8 layer) '(370 . 30)
    '(100 . "AcDbPolyline") (cons 90 (length (cadr stroke))) (cons 70 (if (car stroke) 1 0))))
  (foreach point (cadr stroke)
    (setq data (append data (list (cons 10 (ast:g-add origin point))
      (cons 42 (if (caddr point) (caddr point) 0.0))))))
  (entmakex data))
(defun ast:banner-bounds (guides / guide low high minimum maximum)
  (foreach guide guides
    (vla-GetBoundingBox (vlax-ename->vla-object guide) 'low 'high)
    (setq low (vlax-safearray->list low) high (vlax-safearray->list high)
      minimum (if minimum (mapcar 'min minimum low) low)
      maximum (if maximum (mapcar 'max maximum high) high)))
  (list minimum maximum))
(defun ast:banner-move (guides x y / guide)
  (foreach guide guides
    (vla-Move (vlax-ename->vla-object guide) (vlax-3d-point '(0.0 0.0 0.0)) (vlax-3d-point (list x y 0.0)))))
(defun ast:banner-row (entry / letter strokes stroke guide guides bounds shift height)
  (foreach letter (cadddr entry)
    (setq strokes (if (= (car entry) "YOU")
      (ast:banner-outline (car letter))
      (ast:banner-script (car letter) (cadr entry))))
    (foreach stroke strokes
      (setq guide (ast:banner-poly (ast:show-turn stroke (caddr entry) '(0 0)) (list (cadr letter) 0.0)
        (if (= (car entry) "YOU") "BANNER_YOU" "BANNER_LETTERS")))
      (vla-ScaleEntity (vlax-ename->vla-object guide) (vlax-3d-point '(0.0 0.0 0.0)) (cadr entry))
      (setq guides (append guides (list guide)))))
  (setq bounds (ast:banner-bounds guides)
    shift (- 80.0 (* 0.5 (+ (caar bounds) (caadr bounds))))
    height (- (cadadr bounds) (cadar bounds)))
  (ast:banner-move guides shift (- (cadar bounds)))
  (list (cons 'label (car entry)) (cons 'guides guides) (cons 'height height)))
;;; The even/odd mask keeps O's counter empty as well as the spaces between letters.
(defun ast:banner-mask (outlines / guide primitives polygons route)
  (foreach guide outlines
    (setq route (ast:cad-get 'route (ast:cad-read guide))
      primitives (append primitives (ast:cad-get 'primitives route))
      polygons (cons (ast:emblem-route-polygon (ast:cad-get 'primitives route)) polygons)))
  (list primitives polygons))
(defun ast:banner-inside (point mask / polygon inside)
  (foreach polygon (cadr mask)
    (if (ast:emblem-point-inside point polygon) (setq inside (not inside)))) inside)
(defun ast:banner-inset (point mask inset / clear rest)
  (setq clear (ast:banner-inside point mask) rest (car mask))
  (while (and clear rest)
    (if (< (ast:emblem-point-primitive-distance point (car rest)) inset) (setq clear nil))
    (setq rest (cdr rest))) clear)
(defun ast:banner-subarc (arc start length / radius sign)
  (setq radius (ast:cad-get 'radius arc) sign (if (< (ast:cad-get 'sweep arc) 0.0) -1.0 1.0))
  (list '(kind . arc) (cons 'center (ast:cad-get 'center arc)) (cons 'radius radius)
    (cons 'start-angle (+ (ast:cad-get 'start-angle arc) (* sign (/ start radius))))
    (cons 'sweep (* sign (/ length radius)))))
(defun ast:banner-clip (arc mask inset / total count cell index start runs point run length step gaps extra result)
  (setq total (ast:g-length arc) count (1+ (fix (/ total 0.2))) cell (/ total count) index 0)
  ;; Midpoint padding bounds the whole cell, including the half-slit footprint.
  (repeat count
    (setq point (ast:g-point arc (* (+ index 0.5) cell)))
    (if (ast:banner-inset point mask (+ inset 0.75 (* 0.5 cell)))
      (if (null start) (setq start (* index cell)))
      (if start (setq runs (cons (list start (* index cell)) runs) start nil)))
    (setq index (1+ index)))
  (if start (setq runs (cons (list start total) runs)))
  (setq step (ast:g-step arc 2.7))
  (foreach run (reverse runs)
    (setq length (- (cadr run) (car run)) gaps (ast:g-floor-near (/ length step)))
    ;; Keep even one complete stitch in a tapered arm; trim free ends symmetrically.
    (if (>= gaps 1)
      (progn
        (setq extra (- length (* gaps step)))
        (setq result (cons (ast:banner-subarc arc (+ (car run) (* 0.5 extra)) (* gaps step)) result)))))
  (reverse result))
(defun ast:banner-arc-guide (arc / quarter)
  (setq quarter (* 0.25 (ast:cad-get 'sweep arc)))
  (ast:banner-poly (ast:show-stroke
    (list (append (ast:g-point arc 0.0) (list (/ (sin quarter) (cos quarter))))
          (ast:g-point arc (ast:g-length arc))) nil) '(0.0 0.0) "BANNER_FLOW"))
(defun ast:banner-fill-check (outlines guides / mask plans openings opening point primitive minimum distance error plan gap bounds guide arc center row)
  (setq mask (ast:banner-mask outlines) plans (ast:fill-plans guides nil)
    openings (ast:emblem-openings plans) minimum 1e99 bounds (ast:banner-bounds outlines))
  (foreach guide guides
    (setq arc (car (ast:cad-get 'primitives (ast:cad-get 'route (ast:cad-read guide))))
      center (ast:cad-get 'center arc)
      row (/ (- (cadr center) (- (cadar bounds) 170.0)) 3.0))
    (ast:cad-require (and (equal (ast:cad-get 'radius arc) 170.0 1e-6)
      (equal (car center) 80.0 1e-6) (<= -1e-6 row 30.000001)
      (equal row (float (fix (+ row 0.5))) 1e-6))
      "A fill fragment no longer follows the shared flow field."))
  (ast:cad-require openings "The banner has no stitched fill.")
  (foreach opening openings
    (setq point (ast:cad-get 'center opening))
    (ast:cad-require (ast:banner-inside point mask) "A fill hole is outside YOU.")
    (foreach primitive (car mask)
      (setq distance (- (ast:emblem-point-primitive-distance point primitive)
                        (* 0.5 (ast:cad-get 'length opening)))
        minimum (min minimum distance))))
  (ast:cad-require (>= minimum 3.75) "A fill slit enters the 3.75 mm guide border.")
  (foreach plan plans
    (foreach gap (ast:cad-get 'intervals (ast:cad-get 'solution plan))
      (ast:cad-require (equal 2.7 (ast:cad-get 'distance gap) 1e-7) "A flow gap is not nominal.")))
  (setq error (ast:g-validate-openings openings (ast:banner-settings)))
  (ast:cad-require (null error) "Two fill holes overlap; increase the flow row spacing.")
  (list '(ok . T) (cons 'fill-guides (length guides)) (cons 'openings (length openings))
    (cons 'minimum-outline-clearance minimum) '(pitch . 2.7) '(row-spacing . 3.0)
    '(outline-inset . 3.75) '(combined-clearance . T) '(all-gaps-nominal . T)))
(defun ast:banner-fill (outlines / mask bounds path whole arc fragments fragment guides report)
  (setq mask (ast:banner-mask outlines) bounds (ast:banner-bounds outlines))
  (ast:show-layer "BANNER_FLOW" 8 nil)
  ;; All fragments come from this single translated arc field across the entire word.
  (foreach path (ast:fill-paths "FLOW"
      (list (cons 'start (list 0.0 (- (cadar bounds) 20.0))) '(chord . 160.0)
            '(sag . 20.0) '(rows . 31) '(row-spacing . 3.0)))
    (setq whole (ast:banner-poly (ast:show-stroke path nil) '(0.0 0.0) "BANNER_FLOW")
      arc (car (ast:cad-get 'primitives (ast:cad-get 'route (ast:cad-read whole)))))
    (entdel whole)
    (setq fragments (append fragments (ast:banner-clip arc mask 3.75))))
  (foreach fragment fragments (setq guides (cons (ast:banner-arc-guide fragment) guides)))
  (setq guides (reverse guides))
  (ast:banner-configure guides)
  (setq report (ast:banner-fill-check outlines guides))
  (cons (cons 'plans (ast:fill-plans guides nil)) report))

(defun ast:banner-dot (guide / bounds center radius)
  (setq bounds (ast:banner-bounds (list guide))
    center (ast:g-mul (ast:g-add (car bounds) (cadr bounds)) 0.5)
    radius (* 0.5 (- (caadr bounds) (caar bounds))))
  (list '(type . round) (cons 'center center) (cons 'diameter (* 2.0 radius))))
(defun ast:banner-text-check (text-plans fill-plans dot / text fill error clearance)
  (setq text (ast:emblem-openings text-plans) fill (ast:emblem-openings fill-plans)
    error (ast:g-validate-openings (cons dot (append text fill)) (ast:banner-settings)))
  (ast:cad-require (null error) error)
  (setq clearance (ast:emblem-halo-check fill text dot 3.0))
  (ast:cad-require (ast:cad-get 'ok clearance) "A fill hole is within 3 mm of the outline stitching.")
  (list (cons 'lettering-sources (length text-plans)) (cons 'lettering-openings (length text))
    '(round-dots . 1) '(fill-to-lettering-clearance . 3.0) '(combined-clearance . T)))
(defun ast:banner-shape-check (/ letters guide route bowls primitives first-arc arc other other-arc hit)
  (setq letters (ast:emblem-guides "BANNER_LETTERS"))
  (foreach guide letters
    (setq route (ast:cad-get 'route (ast:cad-read guide)))
    (if (ast:cad-get 'closed route)
      (progn
        (setq bowls (cons guide bowls) primitives (ast:cad-get 'primitives route) first-arc (car primitives))
        (foreach arc primitives
          (ast:cad-require (and (= 'arc (ast:cad-get 'kind arc))
            (equal 10.08 (ast:cad-get 'radius arc) 1e-8)
            (equal (ast:cad-get 'center first-arc) (ast:cad-get 'center arc) 1e-8))
            "An a bowl is no longer a true circle at the shared script size."))
        (ast:cad-require (equal (* 2.0 pi)
          (apply '+ (mapcar '(lambda (arc) (abs (ast:cad-get 'sweep arc))) primitives)) 1e-8)
          "An a bowl is not a complete circle.")
        (foreach other letters
          (if (not (equal guide other))
            (foreach other-arc (ast:cad-get 'primitives (ast:cad-get 'route (ast:cad-read other)))
              (foreach arc primitives
                (setq hit (ast:n-hits arc other-arc))
                (ast:cad-require (and (null (ast:cad-get 'points hit)) (null (ast:cad-get 'overlap hit)))
                  "A lettering stroke crosses an a bowl."))))))))
  (ast:cad-require (= 2 (length bowls)) "The banner needs two round a bowls.")
  (ast:cad-require (= (cadr (car ast:banner-lettering-layout)) (cadr (caddr ast:banner-lettering-layout)))
    "The two script rows must use the same size.")
  T)
;;; Crossings stay on the pitch lattice; free ends use its half-pitch phase.
(defun ast:banner-diamond-runs (anchor direction bounds mask packets / low high a b index finish start point runs)
  (setq a (/ (- (+ (caar bounds) 1.35) (car anchor)) (car direction))
    b (/ (- (- (caadr bounds) 1.35) (car anchor)) (car direction))
    low (min a b) high (max a b)
    a (/ (- (+ (cadar bounds) 1.35) (cadr anchor)) (cadr direction))
    b (/ (- (- (cadadr bounds) 1.35) (cadr anchor)) (cadr direction))
    low (max low (min a b)) high (min high (max a b))
    index (ast:g-ceil-near (/ low 2.7)) finish (ast:g-floor-near (/ high 2.7)))
  (while (< index finish)
    (setq point (ast:g-add anchor (ast:g-mul direction (* 2.7 (+ index 0.5)))))
    ;; The midpoint allowance covers the whole stitch, including its slit footprint.
    (if (ast:emblem-mask-clear point (car mask) (cadr mask) packets 8.85 8.1)
      (if (null start) (setq start index))
      (if start (setq runs (cons (list start index) runs) start nil)))
    (setq index (1+ index)))
  (if start (setq runs (cons (list start finish) runs)))
  (reverse runs))
(defun ast:banner-background-check (plans foreground frame letters / openings error halo bounds opening points point radius guide-count plan mask crossings adjusted gap)
  (setq openings (ast:emblem-openings plans) bounds (ast:banner-bounds (list frame))
    mask (ast:banner-mask letters))
  (ast:cad-require openings "The diamond background is empty.")
  (setq error (ast:g-validate-openings (append foreground openings) (ast:banner-settings)))
  (ast:cad-require (null error) error)
  (setq halo (ast:emblem-halo-check openings foreground nil 6.0))
  (ast:cad-require (ast:cad-get 'ok halo) "A background hole enters the text's 6 mm clear perimeter.")
  (foreach opening openings
    (setq point (ast:cad-get 'center opening))
    (ast:cad-require (not (vl-some '(lambda (polygon) (ast:emblem-point-inside point polygon)) (cadr mask)))
      "A background hole is inside a letter or its counter.")
    (if (= 'slit (ast:cad-get 'type opening))
      (setq points (ast:g-ends opening))
      (progn (setq point (ast:cad-get 'center opening) radius (* 0.5 (ast:cad-get 'diameter opening)))
        (setq points (list (ast:g-add point (list radius radius)) (ast:g-sub point (list radius radius))))))
    (foreach point points
      (ast:cad-require (and (> (car point) (caar bounds)) (< (car point) (caadr bounds))
        (> (cadr point) (cadar bounds)) (< (cadr point) (cadadr bounds)))
        "A background hole extends beyond the outer frame.")))
  (setq guide-count 0 crossings 0 adjusted 0)
  (foreach plan plans
    (setq guide-count (+ guide-count (length (ast:cad-get 'states plan)))
      crossings (+ crossings (length (ast:cad-get 'connections plan))))
    (foreach gap (ast:cad-get 'intervals (ast:cad-get 'solution plan))
      (if (= 'corrected (ast:cad-get 'kind gap)) (setq adjusted (1+ adjusted)))))
  (list (cons 'background-guides guide-count) (cons 'background-blocks (length plans))
    (cons 'background-openings (length openings)) (cons 'background-junctions crossings)
    (cons 'background-adjusted-gaps adjusted) '(background-crossing-spacing . 13.5)
    '(text-perimeter . 6.0) '(frame-contained . T)))
(defun ast:banner-background (letters foreground frame / mask packets bounds center diagonal direction normal k anchor run guides plans report)
  (setq mask (ast:banner-mask letters) packets (ast:emblem-opening-packets foreground)
    bounds (ast:banner-bounds (list frame)) center (ast:g-mul (ast:g-add (car bounds) (cadr bounds)) 0.5)
    diagonal (/ 1.0 (sqrt 2.0)))
  (ast:show-layer "BANNER_DIAMONDS" 8 nil)
  (foreach direction (list (list diagonal diagonal) (list (- diagonal) diagonal))
    (setq normal (ast:g-left direction) k -12)
    (repeat 25
      (setq anchor (ast:g-add center (ast:g-mul normal (* k 13.5))))
      (foreach run (ast:banner-diamond-runs anchor direction bounds mask packets)
        ;; Inset both free ends by half a pitch, retaining at least three gaps.
        (if (>= (- (cadr run) (car run)) 4)
          (setq guides (cons (ast:banner-poly (ast:show-stroke
            (list (ast:g-add anchor (ast:g-mul direction (* 2.7 (+ (car run) 0.5))))
                  (ast:g-add anchor (ast:g-mul direction (* 2.7 (- (cadr run) 0.5))))) nil)
            '(0.0 0.0) "BANNER_DIAMONDS") guides))))
      (setq k (1+ k))))
  (setq guides (reverse guides))
  (ast:banner-configure guides)
  (setq plans (ast:fill-plans guides T) report (ast:banner-background-check plans foreground frame letters))
  (cons (cons 'plans plans) report))

(defun ast:banner-check (/ outlines guides lettering guide state report selection dot text-report background frame text-plans fill-plans background-report)
  (setq outlines (ast:emblem-guides "BANNER_YOU") guides (ast:emblem-guides "BANNER_FLOW")
    lettering (append outlines (ast:emblem-guides "BANNER_LETTERS"))
    background (ast:emblem-guides "BANNER_DIAMONDS") frame (ast:emblem-guides "BANNER_PAGE"))
  (ast:cad-require (= 4 (length outlines)) "The banner needs the four YOU contours.")
  (ast:cad-require (= 1 (length frame)) "The banner needs one outer frame.")
  (ast:cad-require (equal (ast:banner-bounds frame) '((0.0 0.0 0.0) (160.0 200.0 0.0)) 1e-6)
    "The banner frame must be 160 by 200 mm.")
  (ast:banner-shape-check)
  (foreach guide (append guides lettering background)
    (setq state (ast:cad-read guide))
    (ast:cad-require (and (ast:cad-get 'output state) (not (ast:cad-get 'stale state)))
      "A banner guide needs regeneration.")
    (ast:cad-require (equal 2.7 (ast:cad-get 'pitch (ast:cad-get 'settings state)) 1e-8)
      "A banner guide has the wrong pitch."))
  (setq selection (ssget "_X" '((0 . "CIRCLE") (8 . "BANNER_PUNCTUATION"))))
  (ast:cad-require (and selection (= 1 (sslength selection))) "The question mark needs one round dot.")
  (setq dot (ast:banner-dot (ssname selection 0)) report (ast:banner-fill-check outlines guides)
    text-plans (ast:fill-plans lettering T) fill-plans (ast:fill-plans guides nil)
    text-report (ast:banner-text-check text-plans fill-plans dot)
    background-report (ast:banner-background-check (ast:fill-plans background T)
      (cons dot (append (ast:emblem-openings text-plans) (ast:emblem-openings fill-plans))) (car frame) lettering))
  (ast:cad-require (and (= 19 (length lettering)) (= 104 (length guides))
    (= 404 (ast:cad-get 'openings report)) (= 612 (ast:cad-get 'lettering-openings text-report))
    (= 16 (ast:cad-get 'lettering-sources text-report))) "The banner geometry or hole count has changed.")
  (ast:cad-require (and (= 42 (length background)) (= 432 (ast:cad-get 'background-openings background-report))
    (= 11 (ast:cad-get 'background-blocks background-report)) (= 36 (ast:cad-get 'background-junctions background-report)))
    "The background geometry or hole count has changed.")
  (append report text-report background-report))

(defun c:ASTBANNERDEMO (/ entry rows row total cursor guides outlines fill text-plans dot-guide dot report result entity frame background foreground)
  (ast:cad-require (null (ssget "_X" '((410 . "Model")))) "Build the banner in a new empty drawing.")
  (setvar "INSUNITS" 4)
  (ast:show-layer "BANNER_LETTERS" 7 T)
  (ast:show-layer "BANNER_YOU" 7 T)
  (ast:show-layer "BANNER_PAGE" 8 nil)
  (foreach entry ast:banner-lettering-layout
    (setq rows (append rows (list (ast:banner-row entry)))))
  ;; Equal gaps between word extents, with the whole composition centred on the page.
  (setq total (+ 28.0 (apply '+ (mapcar '(lambda (row) (ast:cad-get 'height row)) rows)))
    cursor (+ 100.0 (* 0.5 total)))
  (foreach row rows
    (setq cursor (- cursor (ast:cad-get 'height row)))
    (ast:banner-move (ast:cad-get 'guides row) 0.0 cursor)
    (if (= (ast:cad-get 'label row) "YOU") (setq outlines (ast:cad-get 'guides row)))
    (setq cursor (- cursor 14.0) guides (append guides (ast:cad-get 'guides row))))
  ;; The question-mark dot is one punch, not a tiny loop of slit holes.
  (setq dot-guide (last guides) dot (ast:banner-dot dot-guide) guides (vl-remove dot-guide guides))
  (entdel dot-guide)
  (ast:banner-shape-check)
  (ast:banner-configure guides)
  (setq text-plans (ast:fill-plans guides T) fill (ast:banner-fill outlines)
    report (ast:banner-text-check text-plans (ast:cad-get 'plans fill) dot)
    foreground (cons dot (append (ast:emblem-openings text-plans) (ast:emblem-openings (ast:cad-get 'plans fill))))
    frame (ast:banner-poly (ast:show-stroke '((0 0) (160 0) (160 200) (0 200)) T) '(0.0 0.0) "BANNER_PAGE")
    background (ast:banner-background guides foreground frame)
    result (ast:cad-transaction 'ast:cad-write-components-inner
      (list (append text-plans (ast:cad-get 'plans fill) (ast:cad-get 'plans background)))))
  (ast:cad-require (ast:cad-get 'ok result) (ast:cad-get 'error result))
  (ast:show-layer "BANNER_PUNCTUATION" 7 T)
  (entmakex (list '(0 . "CIRCLE") '(8 . "BANNER_PUNCTUATION")
    (cons 10 (append (ast:cad-get 'center dot) '(0.0))) (cons 40 (* 0.5 (ast:cad-get 'diameter dot)))))
  (ast:cad-write-hole-fill dot 1.0)
  (setq entity (entget (entlast)))
  (entmod (subst '(8 . "BANNER_PUNCTUATION") (assoc 8 entity) entity))
  (vl-cmdf "_.-LAYER" "_OFF" "BANNER_FLOW,BANNER_LETTERS,BANNER_YOU,BANNER_DIAMONDS,AUTOSTITCH_UI" "")
  (setvar "LWDISPLAY" 1) (setvar "UCSICON" 0)
  (vl-cmdf "_.ZOOM" "_W" '(0.0 0.0) '(160.0 200.0))
  (vl-cmdf "_.-VIEW" "_Save" "BANNER")
  (princ "\nBanner lettering, flow fill and diamond background stitched.")
  (append (vl-remove (assoc 'plans fill) fill) report (vl-remove (assoc 'plans background) background)
    (list (cons 'lettering-guides (length guides)) '(page-width . 160.0) '(page-height . 200.0))))
(princ)
