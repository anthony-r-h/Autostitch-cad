;;; Export the actual generated drawing entities for scale-faithful previews.
(defun ast:demo-json (value / text item)
  (cond ((null value) "null")
    ((listp value) (setq text "[")
      (foreach item value (setq text (strcat text (if (= text "[") "" ",") (ast:demo-json item))))
      (strcat text "]"))
    ((= (type value) 'REAL)
      (setq text (rtos value 2 8))
      (cond ((= (substr text 1 1) ".") (strcat "0" text))
            ((= (substr text 1 2) "-.") (strcat "-0" (substr text 2))) (T text)))
    (T (vl-prin1-to-string value))))
(defun ast:demo-export-line (a b width layer file)
  (write-line (ast:demo-json (list "line" layer (car a) (cadr a) (car b) (cadr b) width)) file))
(defun ast:demo-export-entity (entity file reference / data kind layer width points item station next total a b)
  (setq data (entget entity) kind (cdr (assoc 0 data)) layer (cdr (assoc 8 data))
    width (if (and (assoc 370 data) (> (cdr (assoc 370 data)) 0)) (/ (cdr (assoc 370 data)) 100.0) (if reference 0.2 0.09)))
  (cond
    ((= kind "LINE") (ast:demo-export-line (cdr (assoc 10 data)) (cdr (assoc 11 data)) width layer file))
    ((and (= kind "CIRCLE") (or (not reference) (member layer '("SHOWCASE_PATTERN" "BANNER_PUNCTUATION"))))
      (write-line (ast:demo-json (list "circle" layer (car (cdr (assoc 10 data)))
        (cadr (cdr (assoc 10 data))) (cdr (assoc 40 data)))) file))
    ((and (not reference) (= kind "LWPOLYLINE") (= 0 (cdr (assoc 70 data))) (= 2 (cdr (assoc 90 data))))
      (foreach item data (if (= 10 (car item)) (setq points (append points (list (cdr item))))))
      (ast:demo-export-line (car points) (cadr points) 0.3 layer file))
    ((and reference (member kind '("ARC" "CIRCLE" "LWPOLYLINE")))
      (setq station 0.0 total (vlax-curve-getDistAtParam entity (vlax-curve-getEndParam entity)))
      (while (< station total)
        (setq next (min total (+ station 0.3)) a (vlax-curve-getPointAtDist entity station) b (vlax-curve-getPointAtDist entity next))
        (ast:demo-export-line a b width layer file) (setq station next)))))
(defun ast:demo-export (path reference-layers / file selection index entity child data)
  (setq selection (ssget "_X" '((0 . "INSERT") (8 . "AUTOSTITCH"))) index 0)
  (if selection (repeat (sslength selection)
    (ast:cad-require (ast:cad-placement-ok-p (ssname selection index)) "Regenerate displaced stitch blocks before exporting.")
    (setq index (1+ index))))
  (setq file (open path "w") index 0)
  (ast:cad-require file "Cannot open the preview output file.")
  (if selection (repeat (sslength selection)
    (setq entity (ssname selection index) index (1+ index)
      child (tblobjname "BLOCK" (cdr (assoc 2 (entget entity)))))
    (while (and (setq child (entnext child)) (/= "ENDBLK" (cdr (assoc 0 (entget child)))))
      (if (member (cdr (assoc 8 (entget child))) '("AUTOSTITCH" "AUTOSTITCH_STITCHES"))
        (ast:demo-export-entity child file nil)))))
  (setq selection (ssget "_X" '((0 . "LINE,ARC,CIRCLE,LWPOLYLINE"))) index 0)
  (if selection (repeat (sslength selection)
    (setq entity (ssname selection index) index (1+ index))
    (if (member (cdr (assoc 8 (entget entity))) reference-layers) (ast:demo-export-entity entity file T))))
  (close file) path)
(defun c:ASTDEMOEXPORT (/ path)
  (vl-mkdir (strcat ast:*home* "/output"))
  (vl-mkdir (strcat ast:*home* "/output/native"))
  (setq path (strcat ast:*home* "/output/native/demo-export.jsonl"))
  (ast:demo-export path '("SHOWCASE_PATTERN" "BANNER_PUNCTUATION" "FILL_REFERENCES"))
  (princ (strcat "\nExported demo geometry to " path)) (princ))
