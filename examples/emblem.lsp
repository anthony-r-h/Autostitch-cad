;;; Stitched emblem with a clear band around the lettering. Load examples/demo.lsp, then ASTEMBLEMDEMO.
(defun ast:show-stroke (points closed) (list closed points))
(defun ast:emblem-settings ()
  (ast:cad-put 'pitch 2.7 (ast:cad-default-settings)))
(defun ast:show-layer (name color plot)
  (if (not (tblsearch "LAYER" name))
    (entmake (list '(0 . "LAYER") '(100 . "AcDbSymbolTableRecord") '(100 . "AcDbLayerTableRecord")
      (cons 2 name) '(70 . 0) (cons 62 color) '(6 . "Continuous") (cons 290 (if plot 1 0))))))
(defun ast:show-polyline (stroke origin / data point)
  (setq data (list '(0 . "LWPOLYLINE") '(100 . "AcDbEntity") '(8 . "SHOWCASE_GUIDES")
    '(100 . "AcDbPolyline") (cons 90 (length (cadr stroke))) (cons 70 (if (car stroke) 1 0))))
  (foreach point (cadr stroke)
    (setq data (append data (list (cons 10 (mapcar '+ origin (list (car point) (cadr point))))
      (cons 42 (if (caddr point) (caddr point) 0.0))))))
  (entmakex data))
(defun ast:show-outline (letter / outer inner)
  ;; Flat terminals need enough room for both corner constructions and a free gap.
  (cond
    ((= letter "A")
      (setq outer '((0 0) (0 43.8 -1) (27.5 43.8) (27.5 0) (20.3 0) (20.3 21.6) (7.2 21.6) (7.2 0))
            inner '((7.2 29.7) (7.2 43.8 -1) (20.3 43.8) (20.3 29.7))))
    ((= letter "U")
      (setq outer '((0 57.6) (0 13.75 1) (27.5 13.75) (27.5 57.6) (20.3 57.6) (20.3 13.75 -1) (7.2 13.75) (7.2 57.6))))
    ((= letter "T")
      (setq outer '((0 57.6) (29.4 57.6) (29.4 50.4) (18.3 50.4) (18.3 0) (11.1 0) (11.1 50.4) (0 50.4))))
    ((= letter "O")
      (setq outer '((0 0) (27.6 0) (27.6 57.6) (0 57.6))
            inner '((7.25 8.1) (20.35 8.1) (20.35 49.5) (7.25 49.5)))))
  (if inner (list (ast:show-stroke outer T) (ast:show-stroke inner T)) (list (ast:show-stroke outer T))))
(defun ast:show-script (letter)
  (cond
    ((= letter "S") (list (ast:show-stroke '((24 36 2.414213562373095) (12 24 -2.414213562373095) (0 12)) nil)))
    ((= letter "t") (list
      (ast:show-stroke '((0 48) (0 12 0.414213562373095) (12 0 0.414213562373095) (24 12)) nil)
      (ast:show-stroke '((-11.6 30) (11.6 30)) nil)))
    ((= letter "i") (list
      (ast:show-stroke '((0 27) (0 12 0.414213562373095) (12 0 0.414213562373095) (24 12)) nil)))
    ((= letter "c") (list (ast:show-stroke '((20.0755757467552 20.0755757467552 1.496605762665489)
      (11.76 0 0.198912367379658) (20.0755757467552 3.4444242532448) (28.3911514935104 11.76)) nil)))
    ((= letter "h") (list
      (ast:show-stroke '((0 0) (0 47.52)) nil)
      ;; Lengthen the rising stroke for its fixed half-pitch junction neighbour.
      (ast:show-stroke '((0 17.82) (6.48 24.3 -0.668178637919299) (20.8204285604976 18.36) (20.8204285604976 5.94 0.414213562373095)
        (26.7604285604976 0 0.414213562373095) (32.7004285604976 5.94)) nil)))))
(defun ast:show-turn (stroke degrees pivot / angle)
  (setq angle (* pi (/ degrees 180.0)))
  (list (car stroke) (mapcar '(lambda (p / x y)
    (setq x (- (car p) (car pivot)) y (- (cadr p) (cadr pivot)))
    (list (+ (car pivot) (- (* x (cos angle)) (* y (sin angle))))
      (+ (cadr pivot) (* x (sin angle)) (* y (cos angle))) (if (caddr p) (caddr p) 0.0))) (cadr stroke))))
(defun ast:show-square (/ stroke guide guides root roots settings result entry members dot fill crown)
  (setq settings (ast:emblem-settings))
  ;; Preserve the letter shapes; the surrounding rings are clipped after text fitting.
  (foreach entry '(("A" 391.55 4.0 14.0 13.75) ("U" 427.15 14.0 5.0 13.75)
                  ("T" 464.05 14.0 -5.0 14.7) ("O" 502.8 4.0 -14.0 13.8))
    (foreach stroke (ast:show-outline (car entry))
      (setq guide (ast:show-polyline (ast:show-turn stroke (nth 3 entry) (list (nth 4 entry) 0.0))
        (list (cadr entry) (caddr entry))) roots (cons guide roots) guides (cons guide guides))
      (if (= (car entry) "A")
        (progn
          (setq crown (nth 1 (ast:cad-get 'primitives (ast:cad-get 'route (ast:cad-read guide))))
            result (ast:cad-save-inputs guide settings
              (list (list '(primitive . 1) (cons 'station (/ (ast:g-length crown) 2.0))))))
          (ast:cad-require (ast:cad-get 'ok result) (ast:cad-get 'error result))))))
  (foreach entry '(("S" 362.0) ("t" 399.0) ("i" 428.0) ("t" 457.0) ("c" 486.0) ("h" 518.0))
    (setq members (mapcar '(lambda (stroke) (ast:show-polyline (ast:show-turn stroke -12.0 '(0 0))
      (list (cadr entry) -53.0))) (ast:show-script (car entry))) root (car members))
    (foreach guide (cdr members)
      (setq result (ast:cad-connect-guides root guide nil settings nil))
      (ast:cad-require (ast:cad-get 'ok result) (ast:cad-get 'error result)))
    (setq roots (cons root roots) guides (append members guides)))
  ;; One round punch is the tittle, not a small loop of stitch holes.
  (ast:show-layer "SHOWCASE_PATTERN" 7 T)
  (setq dot (list (+ 428.0 (* 39.0 (sin (* pi (/ 12.0 180.0)))))
    (+ -53.0 (* 39.0 (cos (* pi (/ 12.0 180.0)))))))
  (entmakex (list '(0 . "CIRCLE") '(8 . "SHOWCASE_PATTERN") (cons 10 (append dot '(0.0))) '(40 . 1.5)))
  (ast:cad-write-hole-fill (list (cons 'center dot) '(diameter . 3.0)) 1.0)
  (setq fill (entlast))
  (entmod (subst '(8 . "SHOWCASE_PATTERN") (assoc 8 (entget fill)) (entget fill)))
  roots)
;;; Pure emblem circle clipping. Routes contain primitives and closed fields.
(defun ast:emblem-point-inside (point polygon / previous current inside x y)
  (setq previous (last polygon) x (car point) y (cadr point))
  (foreach current polygon
    (if (and (not (eq (> (cadr current) y) (> (cadr previous) y)))
             (< x (+ (car current) (* (- (car previous) (car current))
                     (/ (- y (cadr current)) (- (cadr previous) (cadr current)))))))
      (setq inside (not inside)))
    (setq previous current)) inside)

(defun ast:emblem-route-polygon (primitives / points primitive count index length)
  (foreach primitive primitives
    (setq length (ast:g-length primitive)
          count (if (= (ast:g-get 'kind primitive nil) 'line) 1 (1+ (fix (/ length 0.25))))
          index 0)
    (repeat count
      (setq points (cons (ast:g-point primitive (* length (/ (float index) count))) points)
            index (1+ index))))
  (reverse points))

(defun ast:emblem-point-primitive-distance (point primitive / center vector length radius projected)
  (if (= (ast:g-get 'kind primitive nil) 'line)
    (ast:g-point-segment-distance point (ast:g-get 'a primitive nil) (ast:g-get 'b primitive nil))
    (progn
      (setq center (ast:g-get 'center primitive nil) vector (ast:g-sub point center)
            length (ast:g-norm vector) radius (ast:g-get 'radius primitive nil))
      (if (> length 1e-12)
        (setq projected (ast:g-add center (ast:g-mul vector (/ radius length)))))
      (if (and projected (ast:g-point-on primitive projected)) (abs (- length radius))
        (min (ast:g-dist point (ast:g-point primitive 0.0))
             (ast:g-dist point (ast:g-point primitive (ast:g-length primitive))))))))

(defun ast:emblem-opening-packets (openings / result opening)
  (foreach opening openings
    (setq result (cons (list opening (ast:g-opening-box opening 0.0)
      (if (= (ast:g-get 'type opening nil) 'slit) (ast:g-ends opening))) result)))
  (reverse result))

(defun ast:emblem-mask-clear (point primitives polygons packets guide-distance hole-distance / clear rest packet opening ends box)
  (setq clear T rest primitives)
  (while (and clear rest)
    (if (< (ast:emblem-point-primitive-distance point (car rest)) guide-distance) (setq clear nil))
    (setq rest (cdr rest)))
  ;; Polygon chords stay within 0.125 mm of their true arc boundary. The much
  ;; wider exact primitive buffer excludes any point whose classification differs.
  (setq rest polygons)
  (while (and clear rest)
    (if (ast:emblem-point-inside point (car rest)) (setq clear nil))
    (setq rest (cdr rest)))
  (setq rest packets box (list (car point) (cadr point) (car point) (cadr point) 0.0))
  (while (and clear rest)
    (setq packet (car rest) opening (car packet) ends (caddr packet))
    (if (not (ast:g-box-separated box (cadr packet) hole-distance))
      (if (< (if ends (ast:g-point-segment-distance point (car ends) (cadr ends))
               (- (ast:g-dist point (ast:g-get 'center opening nil))
                  (/ (ast:g-get 'diameter opening 0.0) 2.0))) hole-distance)
        (setq clear nil)))
    (setq rest (cdr rest))) clear)

(defun ast:emblem-circle-runs (routes openings dot center radii settings margin / primitives polygons route packets radius total count cell half-cell index start runs all-runs point circle run first-run last-run half-slit)
  (foreach route routes
    (setq primitives (append primitives (ast:g-get 'primitives route nil)))
    (if (ast:g-get 'closed route nil)
      (setq polygons (cons (ast:emblem-route-polygon (ast:g-get 'primitives route nil)) polygons))))
  (setq packets (ast:emblem-opening-packets (if dot (cons dot openings) openings))
        half-slit (/ (ast:g-get 'slit-length settings 1.5) 2.0))
  (foreach radius radii
    (setq total (* 2.0 pi radius) count (1+ (fix (/ total 0.25))) cell (/ total count)
          half-cell (/ cell 2.0) index 0 start nil runs nil
          circle (list '(kind . arc) (cons 'center center) (cons 'radius radius)
                       '(start-angle . 0.0) (cons 'sweep (* 2.0 pi))))
    (repeat count
      (setq point (ast:g-point circle (* (+ index 0.5) cell)))
      ;; Distance is 1-Lipschitz: the midpoint allowance certifies the whole cell.
      (if (ast:emblem-mask-clear point primitives polygons packets
            (+ margin (* 2.0 half-slit) half-cell) (+ margin half-slit half-cell))
        (if (null start) (setq start (* index cell)))
        (if start (setq runs (cons (list start (* index cell)) runs) start nil)))
      (setq index (1+ index)))
    (if start (setq runs (cons (list start total) runs)))
    (setq runs (reverse runs))
    (if (> (length runs) 1)
      (progn
        (setq first-run (car runs) last-run (last runs))
        (if (and (< (abs (car first-run)) 1e-8) (< (abs (- (cadr last-run) total)) 1e-8))
          (setq runs (cons (list (car last-run) (+ total (cadr first-run)))
                     (reverse (cdr (reverse (cdr runs)))))))))
    (foreach run runs
      (setq all-runs (cons (list '(kind . arc) (cons 'center center) (cons 'radius radius)
        (cons 'start-angle (/ (car run) radius)) (cons 'sweep (/ (- (cadr run) (car run)) radius))) all-runs))))
  (list '(ok . T) (cons 'arcs (reverse all-runs)) (cons 'raw-runs (length all-runs))))

(defun ast:emblem-trim-arcs (arcs settings / kept dropped trimmed primitive step count target difference radius)
  (setq dropped 0 trimmed 0)
  (foreach primitive arcs
    (setq radius (ast:g-get 'radius primitive nil)
          step (ast:g-step primitive (ast:g-get 'pitch settings 3.0))
          count (fix (/ (ast:g-length primitive) step)))
    ;; Tiny remnants look like stray dashes in the emblem thumbnail.
    (if (< count 3) (setq dropped (1+ dropped))
      (progn
        (setq target (* count step) difference (- (ast:g-length primitive) target))
        (if (> difference 1e-8) (setq trimmed (1+ trimmed)))
        (setq kept (cons (list '(kind . arc) (cons 'center (ast:g-get 'center primitive nil))
          (cons 'radius radius)
          (cons 'start-angle (+ (ast:g-get 'start-angle primitive nil) (/ difference (* 2.0 radius))))
          (cons 'sweep (/ target radius))) kept)))))
  (list '(ok . T) (cons 'arcs (reverse kept)) (cons 'raw-runs (length arcs))
        (cons 'dropped dropped) (cons 'trimmed trimmed)))

(defun ast:emblem-circle-arcs (routes openings dot center radii settings margin / raw trimmed)
  (setq raw (ast:emblem-circle-runs routes openings dot center radii settings margin)
        trimmed (ast:emblem-trim-arcs (ast:g-get 'arcs raw nil) settings))
  (list '(ok . T) (cons 'primitives (ast:g-get 'arcs trimmed nil))
    (cons 'runs (ast:g-get 'raw-runs raw 0))
    (cons 'dropped (ast:g-get 'dropped trimmed 0))
    (cons 'trimmed (ast:g-get 'trimmed trimmed 0))))

(defun ast:emblem-halo-check (circle-openings text-openings dot margin / settings packets opening box rest packet error checks)
  (setq settings (list '(thickness . 0.0) (cons 'margin margin))
        packets (ast:emblem-opening-packets (if dot (cons dot text-openings) text-openings)) checks 0)
  (foreach opening circle-openings
    (setq box (ast:g-opening-box opening 0.0) rest packets)
    (while (and rest (null error))
      (setq packet (car rest))
      (if (not (ast:g-box-separated box (cadr packet) margin))
        (setq error (ast:g-clearance opening (car packet) settings) checks (1+ checks)))
      (setq rest (cdr rest))))
  (if error (list '(ok . nil) (cons 'error error) (cons 'checks checks))
    (list '(ok . T) (cons 'checks checks) (cons 'circle-openings (length circle-openings)))))

(defun ast:emblem-guides (layer / selection index guides)
  (setq selection (ssget "_X" (list '(0 . "LWPOLYLINE") (cons 8 layer) '(410 . "Model"))) index 0)
  (if selection (repeat (sslength selection)
    (setq guides (append guides (list (ssname selection index))) index (1+ index))))
  guides)
(defun ast:emblem-dot (/ selection data)
  (setq selection (ssget "_X" '((0 . "CIRCLE") (8 . "SHOWCASE_PATTERN") (410 . "Model"))))
  (ast:cad-require (and selection (= 1 (sslength selection))) "The emblem needs its single round dot.")
  (setq data (entget (ssname selection 0)))
  (list '(type . round) (cons 'center (list (cadr (assoc 10 data)) (caddr (assoc 10 data))))
    (cons 'diameter (* 2.0 (cdr (assoc 40 data))))))
(defun ast:emblem-openings (plans / openings plan)
  (foreach plan plans (setq openings (append openings (ast:cad-get 'openings (ast:cad-get 'solution plan)))))
  openings)
(defun ast:emblem-validate (text-plans ring-plans dot / text-openings ring-openings error halo plan)
  (setq text-openings (ast:emblem-openings text-plans) ring-openings (ast:emblem-openings ring-plans)
    error (ast:g-validate-openings (cons dot (append text-openings ring-openings)) (ast:emblem-settings)))
  (ast:cad-require (null error) error)
  (setq halo (ast:emblem-halo-check ring-openings text-openings dot 6.0))
  (ast:cad-require (ast:cad-get 'ok halo) "A circular stitch enters the lettering's clear band.")
  (foreach plan ring-plans
    (ast:cad-require (vl-every '(lambda (gap) (< (abs (- (ast:cad-get 'distance gap) 2.7)) 1e-8))
      (ast:cad-get 'intervals (ast:cad-get 'solution plan))) "A circle fragment has unexpected adjusted spacing."))
  (list '(ok . T) (cons 'text-sources (length text-plans)) (cons 'text-openings (length text-openings))
    (cons 'circle-arcs (length ring-plans)) (cons 'circle-openings (length ring-openings))
    '(pitch . 2.7) '(halo-mm . 6.0) '(combined-clearance . T) '(circle-gaps-nominal . T)))
(defun ast:emblem-arc-guide (primitive / a b quarter guide data)
  (setq a (ast:g-point primitive 0.0) b (ast:g-point primitive (ast:g-length primitive))
    quarter (/ (ast:cad-get 'sweep primitive) 4.0)
    guide (ast:show-polyline (ast:show-stroke (list (append a (list (/ (sin quarter) (cos quarter)))) b) nil) '(0.0 0.0))
    data (entget guide))
  (ast:cad-require (entmod (subst '(8 . "SHOWCASE_CIRCLES") (assoc 8 data) data)) "Could not create a circle arc guide.")
  guide)
(defun ast:emblem-solve (/ guides guide state result text-plans routes dot clipping arcs primitive ring-plans report old-circles index)
  (setq guides (ast:emblem-guides "SHOWCASE_GUIDES"))
  (ast:cad-require (= 15 (length guides)) "Expected the emblem's fifteen lettering guides.")
  (ast:cad-require (null (ast:emblem-guides "SHOWCASE_CIRCLES")) "Rebuild the emblem in an empty drawing to change its circle clipping.")
  (foreach guide guides
    (setq result (ast:cad-save-inputs guide (ast:emblem-settings) (ast:cad-get 'landmarks (ast:cad-read guide))))
    (ast:cad-require (ast:cad-get 'ok result) (ast:cad-get 'error result))
    (setq state (ast:cad-read guide) routes (cons (ast:cad-get 'route state) routes)))
  (setq text-plans (ast:fill-plans guides T) dot (ast:emblem-dot)
    clipping (ast:emblem-circle-arcs routes (ast:emblem-openings text-plans) dot
      '(461.0 7.07097512664247) '(110.0 95.0 80.0) (ast:emblem-settings) 6.0))
  (ast:show-layer "SHOWCASE_CIRCLES" 8 nil)
  (foreach primitive (ast:cad-get 'primitives clipping)
    (setq arcs (append arcs (list (ast:emblem-arc-guide primitive)))))
  (ast:cad-require arcs "No circular stitching remains outside the lettering.")
  (foreach guide arcs
    (setq result (ast:cad-save-inputs guide (ast:emblem-settings) nil))
    (ast:cad-require (ast:cad-get 'ok result) (ast:cad-get 'error result)))
  (setq ring-plans (ast:fill-plans arcs nil) report (ast:emblem-validate text-plans ring-plans dot)
    result (ast:cad-transaction 'ast:cad-write-components-inner (list (append text-plans ring-plans))))
  (ast:cad-require (ast:cad-get 'ok result) (ast:cad-get 'error result))
  (setq old-circles (ssget "_X" '((0 . "CIRCLE") (8 . "SHOWCASE_CIRCLES"))) index 0)
  (if old-circles (repeat (sslength old-circles)
    (entdel (ssname old-circles index)) (setq index (1+ index))))
  (vl-cmdf "_.-LAYER" "_OFF" "AUTOSTITCH_UI,SHOWCASE_GUIDES,SHOWCASE_CIRCLES" "")
  (vl-cmdf "_.ZOOM" "_W" '(333.0 -120.9290248733575) '(589.0 135.0709751266425))
  (vl-cmdf "_.-VIEW" "_Save" "EMBLEM")
  (setvar "LWDISPLAY" 1) (setvar "UCSICON" 0)
  (append report (list (cons 'masked-runs (ast:cad-get 'runs clipping)) (cons 'dropped-short-arcs (ast:cad-get 'dropped clipping)))))
(defun ast:emblem-check (/ guides rings guide state landmarks marker crown)
  (setq guides (ast:emblem-guides "SHOWCASE_GUIDES") rings (ast:emblem-guides "SHOWCASE_CIRCLES"))
  (ast:cad-require (and (= 15 (length guides)) rings) "The stitched emblem is incomplete.")
  (foreach guide (append guides rings)
    (setq state (ast:cad-read guide))
    (ast:cad-require (and (ast:cad-get 'ok state) (ast:cad-get 'output state)
      (not (ast:cad-get 'stale state)) (not (ast:cad-get 'placement-conflict state))) "An emblem guide needs regeneration.")
    (ast:cad-require (equal 2.7 (ast:cad-get 'pitch (ast:cad-get 'settings state)) 1e-8) "An emblem guide has the wrong pitch.")
    (foreach marker (ast:cad-get 'landmarks state)
      (setq crown (nth (ast:cad-get 'primitive marker) (ast:cad-get 'primitives (ast:cad-get 'route state))))
      (ast:cad-require (and (= 'arc (ast:cad-get 'kind crown))
        (equal (ast:cad-get 'station marker) (/ (ast:g-length crown) 2.0) 1e-8)) "An emblem landmark moved away from its crown apex.")
      (setq landmarks (cons marker landmarks))))
  (ast:cad-require (= 2 (length landmarks)) "The A needs its two crown landmarks.")
  (ast:emblem-validate (ast:fill-plans guides T) (ast:fill-plans rings nil) (ast:emblem-dot)))
(defun c:ASTEMBLEMDEMO ()
  (ast:cad-require (null (ssget "_X" '((410 . "Model")))) "Use a new empty drawing for the emblem.")
  (setvar "INSUNITS" 4)
  (ast:show-layer "SHOWCASE_GUIDES" 8 nil)
  (ast:show-square)
  (ast:emblem-solve)
  (princ "\nEmblem stitched with a 6 mm clear band around the lettering.")
  (princ))
(princ)
