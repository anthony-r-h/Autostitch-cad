;;; Native fill specimens. Load AUTOSTITCH.lsp and its components first.
;;; All dimensions are mm; generated openings use the production solver.
(defun ast:fill-layer ()
  (if (not (tblsearch "LAYER" "FILL_GUIDES"))
    (entmake '((0 . "LAYER") (100 . "AcDbSymbolTableRecord") (100 . "AcDbLayerTableRecord")
      (2 . "FILL_GUIDES") (70 . 0) (62 . 8) (6 . "Continuous") (290 . 0)))))
(defun ast:fill-poly (vertices origin / data point closed)
  (setq closed (equal (list (caar vertices) (cadar vertices)) (list (car (last vertices)) (cadr (last vertices))) 1e-9))
  (if closed (setq vertices (reverse (cdr (reverse vertices)))))
  (setq data (list '(0 . "LWPOLYLINE") '(100 . "AcDbEntity") '(8 . "FILL_GUIDES")
    '(100 . "AcDbPolyline") (cons 90 (length vertices)) (cons 70 (if closed 1 0))))
  (foreach point vertices
    (setq data (append data (list (cons 10 (ast:g-add origin (list (car point) (cadr point))))
      (cons 42 (if (caddr point) (caddr point) 0.0))))))
  (entmakex data))
(defun ast:fill-rotate (point / scale)
  (setq scale (/ 1.0 (sqrt 2.0)))
  (list (+ 48.0 (* scale (- (car point) (cadr point))))
        (+ 48.0 (* scale (+ (car point) (cadr point))))))
(defun ast:fill-flow-row (start chord sag pitch / radius sweep step count half center first last bulge)
  (ast:cad-require (and (> chord 0.0) (> sag 0.0)) "Flow needs a positive chord and sag.")
  (setq radius (/ (+ (* chord chord) (* 4.0 sag sag)) (* 8.0 sag))
        sweep (* 4.0 (atan (/ (* 2.0 sag) chord))))
  (ast:cad-require (<= pitch (* 2.0 radius)) "This flow curve is too tight for the pitch.")
  (setq step (* 2.0 (ast:g-asin (/ pitch (* 2.0 radius))))
        count (ast:g-floor-near (/ sweep step)))
  (ast:cad-require (> count 0) "This flow row has less than one stitch of room.")
  ;; Free ends stop at a whole count of nominal chord gaps; the curve stays fixed.
  (setq half (* 0.5 count step) center (ast:g-add start (list (* 0.5 chord) (- sag radius)))
        first (ast:g-add center (list (- (* radius (sin half))) (* radius (cos half))))
        last (ast:g-add center (list (* radius (sin half)) (* radius (cos half))))
        bulge (- (/ (sin (* 0.5 half)) (cos (* 0.5 half)))))
  (list (append first (list bulge)) last))
(defun ast:fill-maze-paths ()
  ;; Junctions stay on the 6 mm grid. Free ends on connected walls stop half
  ;; a pitch inside the grid endpoints so every remaining ordinary gap is nominal.
  '(((0 1.5) (0 22.5))
    ((0 30) (30 30))
    ((36 6) (36 30))
    ((12 0) (36 0))
    ((0 18) (22.5 18))
    ((6 7.5) (6 18))
    ((13.5 6) (22.5 6))
    ((18 6) (18 12))
    ((13.5 12) (30 12))
    ((30 7.5) (30 16.5))
    ((7.5 24) (28.5 24))
    ((12 18) (12 24))))
(defun ast:fill-paths (kind parameters / paths value low high radius center step cells extension values chord sag allowed parameter)
  (setq allowed (assoc kind '(("MAZE") ("CIRCLES" count center spacing inner-radius)
    ("QUILT" crossing-spacing cells extension) ("FLOW" start chord sag rows row-spacing))))
  (ast:cad-require allowed "Unknown fill recipe.")
  (setq allowed (cdr allowed))
  (foreach parameter parameters
    (ast:cad-require (member (car parameter) allowed) (strcat "Unknown fill parameter: " (vl-prin1-to-string (car parameter)))))
  (cond
    ((= kind "MAZE")
      (setq paths (ast:fill-maze-paths)))
    ((= kind "CIRCLES")
      (setq radius (ast:g-get 'inner-radius parameters 9.0)
        center (ast:g-get 'center parameters '(24.0 24.0))
        step (ast:g-get 'spacing parameters 6.0))
      (repeat (ast:g-get 'count parameters 5)
        (setq paths (append paths (list (list
          (list (+ (car center) radius) (cadr center) 1.0)
          (list (- (car center) radius) (cadr center) 1.0)
          (list (+ (car center) radius) (cadr center)))))
          radius (+ radius step))))
    ((= kind "QUILT")
      (setq step (ast:g-get 'crossing-spacing parameters 6.0) cells (ast:g-get 'cells parameters 7)
        extension (ast:g-get 'extension parameters 4.5) low (* -0.5 cells step) high (- low) value low)
      (repeat (1+ cells) (setq values (append values (list value)) value (+ value step)))
      (setq paths (list (mapcar 'ast:fill-rotate (list (list (- low extension) low) (list (+ high extension) low)))))
      (foreach value values
        (setq paths (append paths (list (mapcar 'ast:fill-rotate (list (list value (- low extension)) (list value (+ high extension))))))))
      (foreach value (cdr values)
        (setq paths (append paths (list (mapcar 'ast:fill-rotate (list (list (- low extension) value) (list (+ high extension) value))))))))
    ((= kind "FLOW")
      (setq center (ast:g-get 'start parameters '(6.0 6.0)) value (cadr center)
        chord (ast:g-get 'chord parameters 36.0) sag (ast:g-get 'sag parameters 3.0))
      (repeat (ast:g-get 'rows parameters 25)
        (setq paths (cons (ast:fill-flow-row (list (car center) value) chord sag 3.0) paths)
          value (+ value (ast:g-get 'row-spacing parameters 3.0)))))
    (T (ast:cad-require nil "Unknown fill recipe.")))
  paths)
(defun ast:fill-guides (kind origin / guides path)
  (foreach path (ast:fill-paths kind nil)
    (setq guides (append guides (list (ast:fill-poly path origin)))))
  guides)
(defun ast:fill-circle-settings (radius settings / half-step)
  (setq half-step (* radius (ast:g-asin (/ (ast:cad-get 'pitch settings) (* 2.0 radius)))))
  ;; Start beside the right-hand landmark so the loop seam does not split a free span.
  (ast:cad-put 'phase (- (* 2.0 pi radius) half-step) settings))
(defun ast:fill-circle-reference (guides / guide route primitive center radius maximum reference points point landmarks settings result)
  (foreach guide guides
    (setq route (ast:cad-get 'route (ast:cad-read guide)) primitive (car (ast:cad-get 'primitives route))
      center (ast:cad-get 'center primitive) radius (ast:cad-get 'radius primitive)
      maximum (max (if maximum maximum 0.0) radius)))
  (if (not (tblsearch "LAYER" "FILL_REFERENCES"))
    (entmake '((0 . "LAYER") (100 . "AcDbSymbolTableRecord") (100 . "AcDbLayerTableRecord")
      (2 . "FILL_REFERENCES") (70 . 0) (62 . 8) (6 . "Continuous"))))
  (setq reference (entmakex (list '(0 . "LINE") '(8 . "FILL_REFERENCES") '(370 . 13)
    (cons 10 (ast:g-add center (list (- (+ maximum 2.0)) 0.0)))
    (cons 11 (ast:g-add center (list (+ maximum 2.0) 0.0))))))
  (ast:cad-require reference "Could not draw the circle landmark reference.")
  (foreach guide guides
    (setq route (ast:cad-get 'route (ast:cad-read guide)) radius (ast:cad-get 'radius (car (ast:cad-get 'primitives route)))
      settings (ast:fill-circle-settings radius (ast:cad-default-settings)) landmarks nil
      points (vlax-invoke (vlax-ename->vla-object guide) 'IntersectWith (vlax-ename->vla-object reference) 0))
    (while points
      (setq point (list (car points) (cadr points) (caddr points)) points (cdddr points)
        landmarks (append landmarks (list (ast:cad-project guide point)))))
    (ast:cad-require (= 2 (length landmarks)) "The diameter must cross each circle twice.")
    (setq result (ast:cad-save-inputs guide settings landmarks))
    (ast:cad-require (ast:cad-get 'ok result) (ast:cad-get 'error result)))
  reference)
(defun ast:fill-plans (guides connected / states connections groups group members group-states group-connections solved plans node)
  (setq states (ast:cad-set-states guides nil (ast:cad-default-settings) nil))
  (ast:cad-set-check states nil)
  (if connected
    (setq connections (ast:cad-get 'connections (ast:cad-all-connections states nil))))
  (setq groups (ast:cad-components (length states) connections))
  (foreach group groups
    (setq members (mapcar '(lambda (index) (nth index guides)) group)
      group-states (mapcar '(lambda (index) (nth index states)) group)
      group-connections nil)
    (foreach node connections
      (if (member (ast:cad-get 'path (car (ast:cad-get 'incidences node))) group)
        (setq group-connections (append group-connections (list node)))))
    (setq group-connections (ast:cad-remap-connections group-connections guides members)
      solved (ast:cad-resolve-set group-states group-connections)
      plans (append plans (list (append (list (cons 'states group-states)) solved)))))
  plans)
(defun ast:fill-bounds (guides / guide low high minimum maximum width center)
  (foreach guide guides
    (vla-GetBoundingBox (vlax-ename->vla-object guide) 'low 'high)
    (setq low (vlax-safearray->list low) high (vlax-safearray->list high)
      minimum (if minimum (mapcar 'min minimum low) low)
      maximum (if maximum (mapcar 'max maximum high) high)))
  (setq width (+ 6.0 (max (- (car maximum) (car minimum)) (- (cadr maximum) (cadr minimum))))
    center (ast:g-mul (ast:g-add minimum maximum) 0.5))
  (list (cons 'origin (ast:g-sub center (list (/ width 2.0) (/ width 2.0)))) (cons 'width width)
    (cons 'guide-width (- (car maximum) (car minimum))) (cons 'guide-height (- (cadr maximum) (cadr minimum)))))
(defun ast:fill-case (kind origin / settings guides plans plan openings result error width bounds)
  (setq settings (ast:cad-default-settings) guides (ast:fill-guides kind origin)
        bounds (ast:fill-bounds guides) width (ast:cad-get 'width bounds))
  (if (= kind "CIRCLES") (ast:fill-circle-reference guides))
  (setq plans (ast:fill-plans guides (member kind '("QUILT" "MAZE"))))
  ;; Fit every component and check clearance before writing any stitch output.
  (foreach plan plans
    (setq openings (append openings (ast:cad-get 'openings (ast:cad-get 'solution plan)))))
  (setq error (ast:g-validate-openings openings settings))
  (ast:cad-require (null error) error)
  (setq result (ast:cad-transaction 'ast:cad-write-components-inner (list plans)))
  (ast:cad-require (ast:cad-get 'ok result) (ast:cad-get 'error result))
  (vl-cmdf "_.ZOOM" "_W" (ast:cad-get 'origin bounds) (ast:g-add (ast:cad-get 'origin bounds) (list width width)))
  (vl-cmdf "_.-VIEW" "_Save" kind)
  (append (list '(ok . T) (cons 'name kind) '(pitch . 3.0)
    (cons 'settings settings) (cons 'guides (length guides)) (cons 'sources (length plans)) (cons 'openings (length openings))) bounds))
(defun c:ASTFILLDEMOS (/ entry kind result results failure)
  (ast:cad-require (null (ssget "_X" '((410 . "Model")))) "Build fills in a new empty drawing.")
  (setvar "INSUNITS" 4) (ast:fill-layer)
  (setq ast:fill-results nil)
  (foreach entry '(("QUILT" 0.0) ("CIRCLES" 320.0) ("MAZE" 480.0) ("FLOW" 640.0))
    (setq kind (car entry) ast:*cad-error* nil
      result (vl-catch-all-apply 'ast:fill-case (list kind (list (cadr entry) 0.0))))
    (if (vl-catch-all-error-p result)
      (setq result (list '(ok . nil) (cons 'name kind) (cons 'error (if ast:*cad-error* ast:*cad-error* (vl-catch-all-error-message result)))) failure T))
    (setq ast:fill-results (append ast:fill-results (list result)))
    (princ (strcat "\n" (vl-prin1-to-string result))))
  (vl-cmdf "_.-LAYER" "_OFF" "AUTOSTITCH_UI,FILL_GUIDES" "")
  (setvar "LWDISPLAY" 1) (setvar "UCSICON" 0)
  (vl-cmdf "_.ZOOM" "_E")
  (list (cons 'ok (null failure)) (cons 'cases ast:fill-results)))
(defun c:ASTQUILTDEMO ()
  (ast:cad-require (null (ssget "_X" '((410 . "Model")))) "Build quilting in a new empty drawing.")
  (setvar "INSUNITS" 4) (ast:fill-layer)
  (ast:fill-case "QUILT" '(0.0 0.0)))
(princ "\nNative fills: ASTFILLDEMOS, ASTQUILTDEMO (empty drawings).")
(princ)
