;;; Fixed lettering specimen. Load AUTOSTITCH.lsp first; build only in an empty drawing.
(defun ast:show-stroke (points closed) (list closed points))
(defun ast:show-glyph (letter angular / w h r bevel)
  (setq w 23.4 h (if ast:show-height ast:show-height 39.6) r 11.7 bevel 7.5)
  (cond
    ((= letter "A") (list
      (ast:show-stroke (if angular (list '(0.0 0.0) (list (/ w 2) h) (list w 0.0))
        (list '(0.0 0.0) (list 0.0 (- h r) -1.0) (list w (- h r)) (list w 0.0))) nil)
      (ast:show-stroke (list (list (if angular (* w 0.17) 0.0) (* h (if angular 0.34 0.42)))
        (list (if angular (* w 0.83) w) (* h (if angular 0.34 0.42)))) nil)))
    ((= letter "U") (list (ast:show-stroke (if angular
      (list (list 0.0 h) '(0.0 0.0) (list w 0.0) (list w h))
      (list (list 0.0 h) (list 0.0 r 1.0) (list w r) (list w h))) nil)))
    ((= letter "T") (list (ast:show-stroke (list (list 0.0 h) (list w h)) nil)
      (ast:show-stroke (list (list (/ w 2) h) (list (/ w 2) 0.0)) nil)))
    ((= letter "O") (list (ast:show-stroke (if angular
      (list '(0.0 0.0) (list w 0.0) (list w h) (list 0.0 h))
      (list (list 0.0 r) (list 0.0 (- h r) -1.0) (list w (- h r)) (list w r -1.0))) T)))
    ((= letter "S") (list (ast:show-stroke (if angular
      (list (list w h) (list 0.0 h) (list 0.0 (/ h 2)) (list w (/ h 2)) (list w 0.0) '(0.0 0.0))
      (list (list (+ (/ w 2) (/ h 4)) (* h 0.75) 2.414213562373095)
        (list (/ w 2) (/ h 2) -2.414213562373095) (list (- (/ w 2) (/ h 4)) (/ h 4)))) nil)))
    ((= letter "I") (list (ast:show-stroke (list (list 0.0 h) (list w h)) nil)
      (ast:show-stroke (list (list (/ w 2) h) (list (/ w 2) 0.0)) nil)
      (ast:show-stroke (list '(0.0 0.0) (list w 0.0)) nil)))
    ((= letter "C") (list (ast:show-stroke (if angular
      (list (list w h) (list bevel h) (list 0.0 (- h bevel)) (list 0.0 bevel) (list bevel 0.0) (list w 0.0))
      (list (list w (- h r) 1.0) (list 0.0 (- h r)) (list 0.0 r 1.0) (list w r))) nil)))
    ((= letter "H") (list (ast:show-stroke (list '(0.0 0.0) (list 0.0 h)) nil)
      (ast:show-stroke (list (list 0.0 (/ h 2)) (list w (/ h 2))) nil)
      (ast:show-stroke (list (list w 0.0) (list w h)) nil)))))
(defun ast:show-layer (name color plot)
  (if (not (tblsearch "LAYER" name))
    (entmake (list '(0 . "LAYER") '(100 . "AcDbSymbolTableRecord") '(100 . "AcDbLayerTableRecord")
      (cons 2 name) '(70 . 0) (cons 62 color) '(6 . "Continuous") (cons 290 (if plot 1 0))))))
(defun ast:show-polyline (stroke origin / data point)
  (setq data (list '(0 . "LWPOLYLINE") '(100 . "AcDbEntity") '(8 . "SHOWCASE_GUIDES")
    '(100 . "AcDbPolyline") (cons 90 (length (cadr stroke))) (cons 70 (if (car stroke) 1 0))))
  (foreach point (cadr stroke)
    (setq data (append data (list (cons 10 (mapcar '+ origin (list (car point) (cadr point))))
      (cons 42 (if (caddr point) (caddr point) 0.0))))))
  (entmakex data))
(defun ast:show-text (point text height)
  (entmakex (list '(0 . "TEXT") '(8 . "SHOWCASE_NOTES") (cons 10 (append point '(0.0)))
    (cons 40 height) (cons 1 text) '(7 . "Standard"))))
(defun ast:show-letter (letter angular origin / guides guide primary result settings landmarks key master)
  (setq settings (ast:cad-default-settings)
        guides (mapcar '(lambda (stroke) (ast:show-polyline stroke origin)) (ast:show-glyph letter angular))
        primary (car guides))
  (foreach guide (cdr guides)
    (setq result (ast:cad-connect-guides primary guide nil settings nil))
    (ast:cad-require (ast:cad-get 'ok result) (ast:cad-get 'error result)))
  (if (= letter "U")
    (progn
      (setq landmarks (list '((primitive . 0) (station . 13.5))
        (list (cons 'primitive 2) (cons 'station (- (if ast:show-height ast:show-height 39.6) (if angular 0.0 11.7) 13.5)))))
      (foreach guide '(0.0 23.4)
        (entmakex (list '(0 . "LINE") '(8 . "SHOWCASE_REFERENCES")
          (cons 10 (list (+ (car origin) guide -1.5) (+ (cadr origin) (- (if ast:show-height ast:show-height 39.6) 13.5)) 0.0))
          (cons 11 (list (+ (car origin) guide 1.5) (+ (cadr origin) (- (if ast:show-height ast:show-height 39.6) 13.5)) 0.0)))))))
  (setq result (ast:cad-save-inputs primary settings landmarks))
  (ast:cad-require (ast:cad-get 'ok result) (ast:cad-get 'error result))
  (setq key (strcat (if angular "angular-T" "round-T") (rtos (if ast:show-height ast:show-height 39.6) 2 1)) master (cdr (assoc key ast:show-masters)))
  (if (and (= letter "T") master)
    (setq result (ast:match-link master primary 1 nil))
    (progn
      (if (= letter "T") (setq ast:show-masters (cons (cons key primary) ast:show-masters)))
      (setq result (ast:cad-generate primary settings landmarks))))
  (write-line (strcat letter " " (vl-prin1-to-string origin) " " (vl-prin1-to-string result)) ast:show-report)
  (ast:cad-require (ast:cad-get 'ok result) (ast:cad-get 'error result))
  primary)
(defun ast:show-word (word angular origin / index letter roots)
  (setq index 1)
  (repeat (strlen word)
    (setq letter (substr word index 1)
          roots (append roots (list (ast:show-letter letter angular (list (+ (car origin) (* (1- index) 31.5)) (cadr origin)))))
          index (1+ index))) roots)
(defun ast:show-outline (letter / outer inner)
  ;; Flat terminals need enough room for both corner constructions and a free gap.
  (cond
    ((= letter "A")
      (setq outer '((0 0) (0 43.8 -1) (27.6 43.8) (27.6 0) (19.5 0) (19.5 21.6) (8.1 21.6) (8.1 0))
            inner '((8.1 29.7) (8.1 43.8 -1) (19.5 43.8) (19.5 29.7))))
    ((= letter "U")
      (setq outer '((0 57.6) (0 13.8 1) (27.6 13.8) (27.6 57.6) (19.5 57.6) (19.5 13.8 -1) (8.1 13.8) (8.1 57.6))))
    ((= letter "T")
      (setq outer '((0 57.6) (32.1 57.6) (32.1 49.5) (20.1 49.5) (20.1 0) (12 0) (12 49.5) (0 49.5))))
    ((= letter "O")
      (setq outer '((0 0) (27.6 0) (27.6 57.6) (0 57.6))
            inner '((8.1 8.1) (19.5 8.1) (19.5 49.5) (8.1 49.5)))))
  (if inner (list (ast:show-stroke outer T) (ast:show-stroke inner T)) (list (ast:show-stroke outer T))))
(defun ast:show-script (letter)
  (cond
    ((= letter "S") (list (ast:show-stroke '((24 36 2.414213562373095) (12 24 -2.414213562373095) (0 12)) nil)))
    ((= letter "t") (list
      (ast:show-stroke '((0 48) (0 12 0.414213562373095) (12 0 0.414213562373095) (24 12)) nil)
      (ast:show-stroke '((-11.7 30) (11.7 30)) nil)))
    ((= letter "i") (list
      (ast:show-stroke '((0 27) (0 12 0.414213562373095) (12 0 0.414213562373095) (24 12)) nil)))
    ((= letter "c") (list (ast:show-stroke '((20.48528137424 20.48528137424 1.496605762665489)
      (12 0 0.198912367379658) (20.48528137424 3.51471862576) (28.97056274848 12)) nil)))
    ((= letter "h") (list
      (ast:show-stroke '((0 0) (0 48)) nil)
      (ast:show-stroke '((0 18) (6 24 -0.668178637919299) (20.48528137424 18) (20.48528137424 6 0.414213562373095)
        (26.48528137424 0 0.414213562373095) (32.48528137424 6)) nil)))))
(defun ast:show-turn (stroke degrees pivot / angle)
  (setq angle (* pi (/ degrees 180.0)))
  (list (car stroke) (mapcar '(lambda (p / x y)
    (setq x (- (car p) (car pivot)) y (- (cadr p) (cadr pivot)))
    (list (+ (car pivot) (- (* x (cos angle)) (* y (sin angle))))
      (+ (cadr pivot) (* x (sin angle)) (* y (cos angle))) (if (caddr p) (caddr p) 0.0))) (cadr stroke))))
(defun ast:show-circle-landmarks (guides circles settings / guide circle points point landmarks result)
  (foreach guide guides
    (setq landmarks nil)
    (foreach circle circles
      (setq points (vlax-invoke (vlax-ename->vla-object guide) 'IntersectWith (vlax-ename->vla-object circle) 0))
      (while points
        (setq point (list (car points) (cadr points) (caddr points)) points (cdddr points)
              landmarks (cons (ast:cad-project guide point) landmarks))))
    (setq result (ast:cad-save-inputs guide settings landmarks))
    (ast:cad-require (ast:cad-get 'ok result) (ast:cad-get 'error result))))
(defun ast:show-square (/ stroke guide guides root roots settings result entry members circles radius dot fill)
  (setq settings (ast:cad-default-settings))
  ;; Circles are pattern references; their intersections constrain the lettering.
  (foreach entry '(("A" 391.5 4.0 14.0 13.8) ("U" 427.1 14.0 5.0 13.8)
                  ("T" 462.7 14.0 -5.0 16.05) ("O" 502.8 4.0 -14.0 13.8))
    (foreach stroke (ast:show-outline (car entry))
      (setq guide (ast:show-polyline (ast:show-turn stroke (nth 3 entry) (list (nth 4 entry) 0.0))
        (list (cadr entry) (caddr entry))) roots (cons guide roots) guides (cons guide guides))))
  (foreach entry '(("S" 362.0) ("t" 399.0) ("i" 428.0) ("t" 457.0) ("c" 486.0) ("h" 518.0))
    (setq members (mapcar '(lambda (stroke) (ast:show-polyline (ast:show-turn stroke -12.0 '(0 0))
      (list (cadr entry) -53.0))) (ast:show-script (car entry))) root (car members))
    (foreach guide (cdr members)
      (setq result (ast:cad-connect-guides root guide nil settings nil))
      (ast:cad-require (ast:cad-get 'ok result) (ast:cad-get 'error result)))
    (setq roots (cons root roots) guides (append members guides)))
  ;; One round punch is the tittle, not a small loop of stitch holes.
  (ast:show-layer "SHOWCASE_PATTERN" 7 T)
  (setq dot (list (+ 428.0 (* 39.0 (sin (* pi (/ 12.0 180.0)))))
    (+ -53.0 (* 39.0 (cos (* pi (/ 12.0 180.0)))))))
  (entmakex (list '(0 . "CIRCLE") '(8 . "SHOWCASE_PATTERN") (cons 10 (append dot '(0.0))) '(40 . 1.5)))
  (ast:cad-write-hole-fill (list (cons 'center dot) '(diameter . 3.0)) 1.0)
  (setq fill (entlast))
  (entmod (subst '(8 . "SHOWCASE_PATTERN") (assoc 8 (entget fill)) (entget fill)))
  (ast:show-layer "SHOWCASE_CIRCLES" 7 T)
  (foreach radius (if ast:show-circle-radii ast:show-circle-radii '(114.0 100.5))
    (setq circles (cons (entmakex (list '(0 . "CIRCLE") '(8 . "SHOWCASE_CIRCLES")
      '(370 . 13) (cons 10 (list 461.0 (if ast:show-circle-y ast:show-circle-y 15.0) 0.0))
      (cons 40 radius))) circles)))
  (ast:show-circle-landmarks guides circles settings)
  (if (not ast:show-art-only)
    (foreach root roots
      (setq result (ast:cad-generate root settings (ast:cad-get 'landmarks (ast:cad-read root))))
      (write-line (strcat "EMBLEM " (vl-prin1-to-string result)) ast:show-report)
      (ast:cad-require (ast:cad-get 'ok result) (ast:cad-get 'error result))))
  roots)
(defun c:ASTSHOWCASEART (/ ast:show-art-only)
  (ast:cad-require (null (ssget "_X" '((0 . "LINE,ARC,CIRCLE,LWPOLYLINE,INSERT")))) "Use a new empty drawing for the artwork.")
  (setvar "INSUNITS" 4)
  (ast:show-layer "SHOWCASE_GUIDES" 8 nil)
  (setq ast:show-art-only T)
  (ast:show-square)
  (princ "\nArtwork created without fitting stitches. ASTSHOWCASEREGEN fits it when ready.") (princ))
(defun c:ASTSHOWCASEARTMORE (/ ast:show-circle-radii ast:show-circle-y)
  ;; Centre on the lettering's actual vertical bounds; keep this proposal unstitched.
  (setq ast:show-circle-radii '(110.0 95.0 80.0) ast:show-circle-y 7.07097512664247)
  (c:ASTSHOWCASEART))
(defun c:ASTSHOWCASEBUILD (/ ast:show-masters ast:show-report ast:show-height result master)
  (ast:cad-require (null (ssget "_X" '((0 . "LINE,ARC,CIRCLE,LWPOLYLINE,INSERT"))))
    "Build the specimen in a new empty drawing.")
  (setvar "INSUNITS" 4)
  (ast:show-layer "SHOWCASE_GUIDES" 8 nil)
  (ast:show-layer "SHOWCASE_REFERENCES" 8 nil)
  (ast:show-layer "SHOWCASE_NOTES" 8 nil)
  (setq ast:show-report (open (strcat ast:*home* "/output/native/showcase-build.txt") "w"))
  (setq result (vl-catch-all-apply '(lambda ()
    (ast:show-text '(-2.0 55.0) "01  /  ROUND" 3.0)
    (ast:show-word "AUTOSTITCH" nil '(0.0 0.0))
    (ast:show-text '(-2.0 -35.0) "02  /  ANGULAR" 3.0)
    (ast:show-word "AUTOSTITCH" T '(0.0 -90.0))
    (setq ast:show-height 57.6)
    (ast:show-text '(370.0 72.0) "03  /  SQUARE" 3.0)
    (ast:show-square)
    (foreach master ast:show-masters
      (setq result (ast:cad-generate (cdr master) (ast:cad-default-settings) nil))
      (ast:cad-require (ast:cad-get 'ok result) (ast:cad-get 'error result)))
    (list '(ok . T))) nil))
  (write-line (if (vl-catch-all-error-p result) (strcat (vl-catch-all-error-message result) " / " (if ast:*cad-error* ast:*cad-error* "")) "DONE") ast:show-report)
  (close ast:show-report)
  (if (vl-catch-all-error-p result) (princ (vl-catch-all-error-message result))
    (progn (vl-cmdf "_.ZOOM" "_E") (princ "\nShowcase built. Save this drawing as the reusable specimen.")))
  (princ))
(defun c:ASTSHOWCASEREGEN (/ selection index guide owners owner info result failed count)
  (setq selection (ssget "_X" '((8 . "SHOWCASE_GUIDES") (0 . "LWPOLYLINE"))) index 0 count 0)
  (if selection
    (repeat (sslength selection)
      (setq guide (ssname selection index) index (1+ index) owner (ast:cad-stitch-owner guide) info (ast:match-info owner))
      (if (eq 'copy (ast:cad-get 'role info)) (setq owner (ast:cad-get 'source info)))
      (if (not (member owner owners)) (setq owners (cons owner owners)))))
  (foreach owner owners
    (setq result (ast:cad-generate owner (ast:cad-get 'settings (ast:cad-read owner)) (ast:cad-get 'landmarks (ast:cad-read owner))))
    (if (ast:cad-get 'ok result) (setq count (1+ count))
      (setq failed (cons (ast:cad-get 'error result) failed))))
  (princ (strcat "\nShowcase: " (itoa count) " source stitch lines regenerated; " (itoa (length failed)) " failures."))
  (foreach result failed (princ (strcat "\n" result)))
  (list (cons 'ok (null failed)) (cons 'sources count) (cons 'failures failed)))
(princ "\nShowcase: ASTSHOWCASEBUILD (empty drawing), ASTSHOWCASEREGEN (saved specimen).")
(princ)
(defun ast:show-json (value / text item)
  (cond ((null value) "null")
    ((listp value) (setq text "[")
      (foreach item value (setq text (strcat text (if (= text "[") "" ",") (ast:show-json item))))
      (strcat text "]"))
    ((= (type value) 'REAL)
      (setq text (rtos value 2 8))
      (cond ((= (substr text 1 1) ".") (strcat "0" text))
            ((= (substr text 1 2) "-.") (strcat "-0" (substr text 2))) (T text)))
    (T (vl-prin1-to-string value))))
(defun ast:show-export-entity (data file / kind layer points item)
  (setq kind (cdr (assoc 0 data)) layer (cdr (assoc 8 data)))
  (cond
    ((= kind "LINE") (write-line (ast:show-json (list "line" layer
      (car (cdr (assoc 10 data))) (cadr (cdr (assoc 10 data)))
      (car (cdr (assoc 11 data))) (cadr (cdr (assoc 11 data)))
      (if (and (assoc 370 data) (> (cdr (assoc 370 data)) 0)) (/ (cdr (assoc 370 data)) 100.0) 0.09))) file))
    ((and (= kind "CIRCLE") (member layer '("AUTOSTITCH" "SHOWCASE_PATTERN")))
      (write-line (ast:show-json (list "circle" layer (car (cdr (assoc 10 data)))
        (cadr (cdr (assoc 10 data))) (cdr (assoc 40 data)))) file))
    ((and (= kind "LWPOLYLINE") (= 0 (cdr (assoc 70 data))) (= 2 (cdr (assoc 90 data))))
      (foreach item data (if (= 10 (car item)) (setq points (append points (list (cdr item))))))
      (write-line (ast:show-json (append (list "line" layer) (car points) (cadr points) '(0.30))) file))))
(defun ast:show-export-pattern (file / selection index entity station next a b total)
  (setq selection (ssget "_X" '((-4 . "<OR") (-4 . "<AND") (0 . "CIRCLE") (8 . "SHOWCASE_PATTERN") (-4 . "AND>")
    (-4 . "<AND") (0 . "CIRCLE") (8 . "SHOWCASE_CIRCLES") (-4 . "AND>") (-4 . "OR>"))) index 0)
  (if selection (repeat (sslength selection)
    (setq entity (ssname selection index) index (1+ index))
    (if (= "SHOWCASE_CIRCLES" (cdr (assoc 8 (entget entity))))
      (progn
        (setq station 0.0 total (vlax-curve-getDistAtParam entity (vlax-curve-getEndParam entity)))
        (while (< station total)
          (setq next (min total (+ station 0.4)) a (vlax-curve-getPointAtDist entity station)
                b (vlax-curve-getPointAtDist entity next))
          (write-line (ast:show-json (list "line" "SHOWCASE_CIRCLES" (car a) (cadr a) (car b) (cadr b) 0.13)) file)
          (setq station next)))
      (ast:show-export-entity (entget entity) file)))))
(defun c:ASTSHOWCASEARTEXPORT (/ selection index guide total station next a b file)
  (setq file (open (strcat ast:*home* "/output/native/showcase-art.jsonl") "w")
    selection (ssget "_X" '((0 . "LWPOLYLINE") (8 . "SHOWCASE_GUIDES"))) index 0)
  (if selection (repeat (sslength selection)
    (setq guide (ssname selection index) index (1+ index) station 0.0
      total (vlax-curve-getDistAtParam guide (vlax-curve-getEndParam guide)))
    (while (< station total)
      (setq next (min total (+ station 0.4)) a (vlax-curve-getPointAtDist guide station) b (vlax-curve-getPointAtDist guide next))
      (write-line (ast:show-json (list "line" "AUTOSTITCH" (car a) (cadr a) (car b) (cadr b) 0.4)) file)
      (setq station next))))
  (ast:show-export-pattern file) (close file) (princ))
(defun c:ASTSHOWCASEEXPORT (/ selection index entity data child file)
  (setq selection (ssget "_X" '((0 . "INSERT") (8 . "AUTOSTITCH"))) index 0)
  ;; Generated blocks store world coordinates; regenerate moved output before export.
  (if selection
    (repeat (sslength selection)
      (ast:cad-require (ast:cad-placement-ok-p (ssname selection index))
        "Run ASTSHOWCASEREGEN before export; a stitch block was moved, rotated or resized.")
      (setq index (1+ index))))
  (setq file (open (strcat ast:*home* "/output/native/showcase.jsonl") "w") index 0)
  (if selection
    (repeat (sslength selection)
      (setq entity (ssname selection index) index (1+ index)
        child (tblobjname "BLOCK" (cdr (assoc 2 (entget entity)))))
      (while (and (setq child (entnext child)) (/= "ENDBLK" (cdr (assoc 0 (setq data (entget child))))))
        (ast:show-export-entity data file))))
  (ast:show-export-pattern file)
  (close file) (princ "\nExported the actual DWG stitching to output/native/showcase.jsonl.") (princ))
