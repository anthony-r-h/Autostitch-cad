;;; Rebuild the selected Velvet banner with real circular-arc stitch guides.
;;; The lettering below is authored outline geometry; no installed font is needed.
(defun ast:velvet-layer (name weight / entry)
  (if (not (tblsearch "LAYER" name))
    (entmake (list '(0 . "LAYER") '(100 . "AcDbSymbolTableRecord") '(100 . "AcDbLayerTableRecord")
      (cons 2 name) '(70 . 0) '(62 . 7) '(6 . "Continuous") (cons 370 weight)
      (cons 290 (if (member name '("VELVET_GUIDES" "VELVET_LETTERS")) 0 1))))))
(defun ast:velvet-poly (points closed layer / data point)
  (setq data (list '(0 . "LWPOLYLINE") '(100 . "AcDbEntity") (cons 8 layer)
    '(100 . "AcDbPolyline") (cons 90 (length points)) (cons 70 (if closed 1 0))))
  (foreach point points (setq data (append data (list (cons 10 (list (car point) (cadr point)))
    (cons 42 (if (caddr point) (caddr point) 0.0))))))
  (entmakex data))
(defun ast:velvet-primitive (item scale)
  (list '(kind . arc) (cons 'center (mapcar '(lambda (v) (* scale v)) (car item)))
    (cons 'radius (* scale (cadr item))) (cons 'start-angle (caddr item)) (cons 'sweep (cadddr item))))
(defun ast:velvet-trim (primitive target / radius sweep start difference)
  (setq radius (ast:g-get 'radius primitive nil) sweep (ast:g-get 'sweep primitive nil)
    start (ast:g-get 'start-angle primitive nil) difference (- (ast:g-length primitive) target))
  (ast:cad-put 'start-angle (+ start (* (ast:g-sign sweep) (/ difference (* 2 radius))))
    (ast:cad-put 'sweep (* (ast:g-sign sweep) (/ target radius)) primitive)))
(defun ast:velvet-clearance (openings settings / boxes opening bounds index tail rest error width margin tolerance)
  ;; Each source already passed the core's 2000-hole limit. Check all independent
  ;; sources together without treating the whole banner as one stitch line.
  (setq index 0 tolerance 0.0 width (ast:g-get 'thickness settings 0.0) margin (ast:g-get 'margin settings 0.0))
  (if (null width) (setq width 0.0)) (if (null margin) (setq margin 0.0))
  (foreach opening openings
    (setq bounds (ast:g-opening-box opening width) tolerance (max tolerance (nth 4 bounds))
      boxes (cons (list (car bounds) (caddr bounds) index opening bounds) boxes) index (1+ index)))
  (setq tail (vl-sort boxes '(lambda (aa bb) (if (= (car aa) (car bb)) (< (caddr aa) (caddr bb)) (< (car aa) (car bb))))))
  (while (and tail (null error))
    (setq rest (cdr tail))
    (while (and rest (null error) (<= (caar rest) (+ (cadar tail) (max margin 1e-9) (* 2 tolerance))))
      (if (not (ast:g-box-separated (nth 4 (car tail)) (nth 4 (car rest)) margin))
        (setq error (ast:g-clearance (nth 3 (car tail)) (nth 3 (car rest)) settings)))
      (setq rest (cdr rest)))
    (setq tail (cdr tail))) error)
(defun ast:velvet-clearance-tests (/ settings profile primitive slit near far round cases openings checks)
  (setq settings (ast:cad-default-settings) checks 0
    primitive '((kind . line) (a 0.0 0.0) (b 30.0 0.0))
    slit (ast:g-slit primitive 0.0 settings) near (ast:g-slit primitive 0.1 settings)
    far (ast:g-slit primitive 3.0 settings)
    round '((type . round) (center 0.0 0.0) (diameter . 0.5))
    cases (list nil (list slit) (list slit far) (list slit slit) (list near slit)
      (list round slit) (list round far) (list far slit round)
      (list round '((type . round) (center 0.5000000001 0.0) (diameter . 0.5)))))
  (foreach profile (list settings (append '((margin . 0.2) (thickness . 0.1)) settings))
    (foreach openings cases
      (ast:cad-require (equal (ast:velvet-clearance openings profile) (ast:g-validate-openings openings profile))
        "Banner aggregate clearance disagrees with the core checker.")
      (setq checks (1+ checks))))
  (list '(ok . T) (cons 'checks checks)))
(defun ast:velvet-point-inside (point polygon / previous current inside x y)
  (setq previous (last polygon) x (car point) y (cadr point))
  (foreach current polygon
    (if (and (not (eq (> (cadr current) y) (> (cadr previous) y)))
             (< x (+ (car current) (* (- (car previous) (car current))
                     (/ (- y (cadr current)) (- (cadr previous) (cadr current)))))))
      (setq inside (not inside)))
    (setq previous current)) inside)
(defun ast:velvet-glyph-check (plan scale / openings item polygon points previous current segment segments boxes xs ys bounds center ends box inside minimum checks distance)
  (setq minimum 1e99 checks 0)
  (foreach item (ast:cad-get 'plans plan)
    (setq openings (append openings (ast:cad-get 'openings (ast:cad-get 'solution item)))))
  (foreach polygon ast:velvet-letters
    (setq points (mapcar '(lambda (p) (mapcar '(lambda (v) (* scale v)) p)) polygon)
      previous (last points) segments nil xs (mapcar 'car points) ys (mapcar 'cadr points))
    (foreach current points
      (setq bounds (list (min (car previous) (car current)) (min (cadr previous) (cadr current))
        (max (car previous) (car current)) (max (cadr previous) (cadr current)) 1e-10))
      (if (> (distance previous current) 1e-10)
        (setq segments (cons (list previous current bounds) segments)))
      (setq previous current))
    (setq boxes (cons (list points (list (apply 'min xs) (apply 'min ys) (apply 'max xs) (apply 'max ys) 1e-10) segments) boxes)))
  (foreach item openings
    (ast:cad-require (eq (ast:cad-get 'type item) 'slit) "Unexpected non-slit opening in the Velvet fill.")
    (setq center (ast:cad-get 'center item) ends (ast:g-ends item) box (ast:g-opening-box item 0.0) inside nil)
    (foreach polygon boxes
      (setq bounds (cadr polygon))
      (if (and (<= (car bounds) (car center) (caddr bounds)) (<= (cadr bounds) (cadr center) (cadddr bounds))
               (ast:velvet-point-inside center (car polygon)))
        (setq inside (not inside)))
      (if (not (ast:g-box-separated box bounds minimum))
        (foreach segment (caddr polygon)
          (if (not (ast:g-box-separated box (caddr segment) minimum))
            (setq distance (ast:g-segment-distance (car ends) (cadr ends) (car segment) (cadr segment))
                  minimum (min minimum distance))))))
    (ast:cad-require (not inside) "A Velvet opening lies inside a letter.")
    (setq checks (1+ checks)))
  (ast:cad-require (> minimum 1e-8) "A Velvet slit touches a letter boundary.")
  (list '(ok . T) (cons 'opening-checks checks) (cons 'minimum-slit-to-letter minimum)
    (cons 'source-arc-candidates (length ast:velvet-arcs)) (cons 'reference-contours (length ast:velvet-letters))))
(defun ast:velvet-glyph-tests ()
  (ast:velvet-glyph-check (ast:velvet-plan ast:velvet-default-scale (ast:cad-default-settings)) ast:velvet-default-scale))
(defun ast:velvet-plan (scale settings / plans openings dropped trimmed maximum item primitive length solution target count trim result)
  (setq dropped 0 trimmed 0 maximum 0.0)
  (foreach item ast:velvet-arcs
    (setq primitive (ast:velvet-primitive item scale) length (ast:g-length primitive))
    (if (< length (* 0.9 (ast:cad-get 'pitch settings)))
      (setq dropped (1+ dropped))
      (progn
        (setq solution (ast:g-solve (list (cons 'primitives (list primitive))) settings nil) trim 0.0)
        (if (not (ast:cad-get 'ok solution))
          (progn
            ;; Short fragments can fall between permissible interval counts.
            ;; Shorten their authored guide symmetrically; never move a hole off it.
            (setq count (fix (/ length (ast:cad-get 'pitch settings)))
              target (* count 2.0 (ast:cad-get 'radius primitive)
                (ast:g-asin (/ (* 1.099999999 (ast:cad-get 'pitch settings)) (* 2.0 (ast:cad-get 'radius primitive)))))
              trim (- length target))
            (ast:cad-require (and (> count 0) (> target 0.0) (>= trim 0.0)) "Velvet fragment cannot be shortened to a permitted gap count.")
            (setq primitive (ast:velvet-trim primitive target)
              solution (ast:g-solve (list (cons 'primitives (list primitive))) settings nil)
              trimmed (1+ trimmed) maximum (max maximum trim))))
        (ast:cad-require (ast:cad-get 'ok solution) (ast:cad-get 'error solution))
        (setq plans (cons (list (cons 'primitive primitive) (cons 'solution solution)) plans)
              openings (append openings (ast:cad-get 'openings solution))))))
  (setq result (ast:velvet-clearance openings settings))
  (ast:cad-require (null result) result)
  (list (cons 'plans (reverse plans)) (cons 'openings (length openings))
    (cons 'dropped dropped) (cons 'trimmed trimmed) (cons 'maximum-trim maximum)))
(defun ast:velvet-build (scale report / settings result glyph-check plan primitive a b quarter guide output polygon points inset radius x0 x1 y0 y1 bulge)
  (ast:cad-require (null (ssget "_X" '((410 . "Model")))) "Build Velvet in a new empty drawing.")
  (setvar "INSUNITS" 4)
  (setq settings (ast:cad-default-settings) result (ast:velvet-plan scale settings)
    glyph-check (ast:velvet-glyph-check result scale))
  (write-line (vl-prin1-to-string (list (cons 'page-width (* 200 scale)) (cons 'page-height (* 320 scale))
    '(pitch . 3.0) '(slit-length . 1.5) (cons 'row-spacing (* 2.8 scale))
    (cons 'guides (length (ast:cad-get 'plans result))) (cons 'openings (ast:cad-get 'openings result))
    (cons 'dropped-short-fragments (ast:cad-get 'dropped result)) (cons 'trimmed-guides (ast:cad-get 'trimmed result))
    (cons 'maximum-total-trim (ast:cad-get 'maximum-trim result)) '(combined-clearance . T)
    (cons 'minimum-slit-to-letter (ast:cad-get 'minimum-slit-to-letter glyph-check)))) report)
  (ast:velvet-layer "VELVET_GUIDES" 9)
  (ast:velvet-layer "VELVET_LETTERS" 13)
  (ast:velvet-layer "VELVET_FRAME" 13)
  (foreach polygon ast:velvet-letters
    (ast:velvet-poly (mapcar '(lambda (p) (mapcar '(lambda (v) (* scale v)) p)) polygon) T "VELVET_LETTERS"))
  (foreach inset '(7.0 11.0)
    (setq radius (* scale (if (= inset 7.0) 12.0 9.0)) x0 (* scale inset) x1 (* scale (- 200 inset))
      y0 (* scale inset) y1 (* scale (- 320 inset)) bulge (/ (sin (/ pi 8.0)) (cos (/ pi 8.0))))
    (ast:velvet-poly (list (list (+ x0 radius) y0) (list (- x1 radius) y0 bulge)
      (list x1 (+ y0 radius)) (list x1 (- y1 radius) bulge) (list (- x1 radius) y1)
      (list (+ x0 radius) y1 bulge) (list x0 (- y1 radius)) (list x0 (+ y0 radius) bulge)) T "VELVET_FRAME"))
  (foreach plan (ast:cad-get 'plans result)
    (setq primitive (ast:cad-get 'primitive plan) a (ast:g-point primitive 0.0)
      b (ast:g-point primitive (ast:g-length primitive)) quarter (/ (ast:cad-get 'sweep primitive) 4.0)
      guide (ast:velvet-poly (list (append a (list (/ (sin quarter) (cos quarter)))) b) nil "VELVET_GUIDES")
      output (ast:cad-generate guide settings nil))
    (ast:cad-require (ast:cad-get 'ok output) (ast:cad-get 'error output)))
  (vl-cmdf "_.-LAYER" "_OFF" "VELVET_GUIDES,VELVET_LETTERS,AUTOSTITCH_UI" "")
  (setvar "LWDISPLAY" 1)(setvar "UCSICON" 0)
  (vl-cmdf "_.ZOOM" "_W" '(0.0 0.0) (list (* 200 scale) (* 320 scale)))
  (vl-cmdf "_.-VIEW" "_Save" "VELVET")
  (append (list '(ok . T) (cons 'page-width (* 200 scale)) (cons 'page-height (* 320 scale))
      (cons 'guides (length (ast:cad-get 'plans result))) (cons 'source-arc-candidates (length ast:velvet-arcs))
      (cons 'reference-contours (length ast:velvet-letters)) '(pitch . 3.0) '(slit-length . 1.5)
      (cons 'row-spacing (* 2.8 scale)) '(combined-clearance . T)
      (cons 'minimum-slit-to-letter (ast:cad-get 'minimum-slit-to-letter glyph-check)))
    (vl-remove-if '(lambda (pair) (eq (car pair) 'plans)) result)))
(defun c:ASTVELVETDEMO (/ report result)
  (vl-mkdir (strcat ast:*home* "/output"))
  (vl-mkdir (strcat ast:*home* "/output/native"))
  (setq report (open (strcat ast:*home* "/output/native/velvet-report.txt") "w")
    result (vl-catch-all-apply 'ast:velvet-build (list ast:velvet-default-scale report)))
  (write-line (if (vl-catch-all-error-p result)
    (strcat "FAIL " (vl-catch-all-error-message result) " / " (if ast:*cad-error* ast:*cad-error* "")) "DONE") report)
  (close report)
  (if (vl-catch-all-error-p result)
    (setq result (list '(ok . nil) (cons 'error (strcat (vl-catch-all-error-message result) " / " (if ast:*cad-error* ast:*cad-error* ""))))))
  (princ) result)

(setq ast:velvet-default-scale 0.8)

;;; Authored Cooper outlines, opened counters and tracked letters for stitched readability.
;;; Exact circular rows: source spacing 2.8 mm, 1.125 mm exclusion around lettering.
(setq ast:velvet-letters '(
  ((54.7475104464 276.98) (57.1308093248 276.83) (59.4586826479 276.35) (61.7588431933 275.54) (64.0035781834 274.43) (65.804908731 273.5) (66.9411326149 273.2) (67.7170903893 273.29) (68.8256014955 273.56) (69.7955487134 273.68) (70.6269320431 273.56) (71.4028898175 273.2) (72.0957092589 272.6) (72.7608159226 271.76) (74.1464548054 269.3) (75.144114801 266.54) (75.7260831317 263.51) (75.9200725753 260.21) (75.7537959094 257.93) (75.2272531339 256.01) (74.3958698043 254.39) (73.2042203651 253.1) (71.6245920387 252.2) (69.8786870464 251.9) (68.3544842753 252.11) (67.1628348362 252.77) (66.1374620629 254) (65.1120892896 255.92) (64.4469826259 257.39) (63.8650142951 258.65) (63.310758742 259.67) (62.8396415219 260.48) (61.8419815263 261.77) (60.6503320871 262.97) (59.0429909831 264.17) (57.4079371014 265.01) (55.7174576644 265.52) (53.9992654497 265.7) (52.3919243457 265.52) (50.9785726853 264.95) (49.7037849131 264.02) (48.6229865846 262.73) (47.7638904772 261.11) (47.1542093688 259.22) (46.7662304816 257.09) (46.655379371 254.72) (46.8216560369 251.33) (47.3759115901 248.09) (48.262720475 245) (49.5097954695 242.06) (50.5351682428 240.26) (51.643679349 238.7) (52.8907543435 237.41) (54.220967671 236.33) (55.6343193314 235.49) (57.1862348801 234.89) (58.8490015395 234.53) (60.5949065318 234.41) (63.2276204091 234.68) (65.8603342863 235.49) (68.1882076094 236.72) (69.9063998241 238.28) (71.0426237079 239.36) (71.5414537057 239.66) (71.9571453706 239.75) (73.0102309215 239.42) (73.9247525841 238.43) (74.5344336925 236.99) (74.7284231361 235.28) (74.4512953596 232.79) (73.5921992523 230.06) (72.3174114801 227.48) (70.8486342644 225.53) (70.4052298219 225.2) (69.7955487134 224.87) (68.9918781614 224.6) (67.9942181658 224.33) (66.5531537277 223.79) (64.6686848472 222.83) (62.2022476358 221.6) (59.7080976468 220.7) (57.1585221025 220.16) (54.5535210029 219.98) (51.809956015 220.16) (49.0941038047 220.73) (46.3505388168 221.69) (43.6346866066 223.01) (40.6417066197 224.99) (37.9812799648 227.42) (35.6256938641 230.33) (33.6303738729 233.72) (32.0507455465 237.26) (30.9145216626 240.89) (30.2217022212 244.61) (30 248.42) (30.2771277766 252.77) (31.1362238839 256.94) (32.5495755443 260.9) (34.5448955355 264.65) (36.678779415 267.65) (39.089791071 270.29) (41.8056432813 272.54) (44.8263360457 274.43) (47.2650604794 275.54) (49.7037849131 276.35) (52.1979349021 276.83) (54.7475104464 276.98))
  ((102.01417638 261.08) (104.757741368 260.87) (107.307316912 260.21) (109.607477458 259.1) (111.685935782 257.57) (113.487266329 255.53) (114.623490213 253.25) (115.011469101 251.93) (115.260884099 250.37) (115.427160765 248.57) (115.482586321 246.56) (115.399447988 240.59) (115.454873543 237.74) (115.593437431 235.46) (115.815139653 233.72) (116.119980207 232.52) (116.480246316 231.8) (116.812799648 231.38) (117.339342424 231.14) (118.198438531 230.93) (118.974396305 230.42) (119.251524082 229.25) (118.946683528 227.27) (117.97673631 225.23) (116.535671872 223.31) (114.706628546 221.75) (113.459553552 220.97) (112.18476578 220.43) (110.909978007 220.1) (109.57976468 219.98) (107.944710798 220.16) (106.475933583 220.7) (105.20114581 221.6) (104.120347482 222.89) (103.455240818 223.67) (102.84555971 223.91) (102.069601935 223.67) (101.099654717 222.92) (99.4091752804 221.63) (97.5801319551 220.73) (95.6679502969 220.16) (93.644917528 219.98) (91.5941719815 220.13) (89.7651286563 220.55) (88.1300747746 221.24) (86.6890103365 222.23) (85.1370947878 223.94) (83.9454453486 226.1) (83.1694875742 228.56) (82.9200725753 231.11) (83.0863492413 233.15) (83.6128920167 235.04) (84.471988124 236.84) (85.6636375632 238.49) (88.1023619969 240.71) (91.0399164284 242.3) (94.531726413 243.26) (98.5500791731 243.59) (99.4091752804 243.62) (100.074281944 243.71) (100.60082472 243.83) (100.933378051 244.04) (101.321356939 244.82) (101.432208049 246.2) (101.376782494 248.18) (101.238218606 249.86) (101.016516384 251.24) (100.71167583 252.35) (100.295984165 253.19) (99.7417286123 253.79) (99.1043347262 254.15) (98.3560897295 254.27) (97.4138552892 254.09) (96.5824719595 253.55) (95.7233758522 252.53) (94.6702903013 250.88) (93.2015130856 248.66) (91.6773103145 247.07) (90.1531075434 246.14) (88.5734792171 245.81) (87.1047020013 246.08) (85.9407653398 246.95) (85.1648075654 248.3) (84.9153925665 250.01) (85.2202331207 251.93) (86.1901803387 253.85) (87.6589575544 255.68) (89.626564768 257.24) (92.6195447548 258.92) (95.6956630746 260.12) (98.8272069496 260.84) (102.01417638 261.08))
  ((100.385598336 238.255) (99.2547074957 238.15728013) (98.1690522885 237.864120521) (97.1738683487 237.375521173) (96.2691556761 236.658908795) (95.0025579344 234.93252443) (94.5502015981 232.912980456) (94.8668510335 231.023729642) (95.7715637061 229.557931596) (97.2191039823 228.580732899) (99.0285293275 228.255) (100.883190306 228.613306189) (102.240259315 229.720798046) (103.054500721 231.57747557) (103.325914522 234.150765472) (103.144971988 236.137736156) (102.692615652 237.375521173) (101.833138613 237.994413681) (100.385598336 238.255))
  ((166.629041126 246.23) (167.100158346 232.1) (167.238722234 230.72) (167.515850011 229.73) (168.180956675 228.62) (169.511170002 226.82) (169.899148889 226.04) (170.01 224.99) (169.843723334 223.79) (169.372606114 222.77) (168.568935562 221.93) (167.432711678 221.3) (165.880796129 220.85) (163.802337805 220.52) (161.252762261 220.34) (158.176643941 220.28) (156.070472839 220.34) (154.324567847 220.52) (152.883503409 220.82) (151.774992303 221.24) (150.915896195 221.81) (150.306215087 222.53) (149.945948977 223.43) (149.835097867 224.48) (149.890523422 225.17) (150.02908731 225.68) (150.472491753 226.34) (151.33158786 227.54) (151.636428414 228.08) (151.913556191 228.86) (152.135258412 229.91) (152.329247856 231.17) (152.467811744 232.7) (152.578662855 234.47) (152.63408841 236.51) (152.661801188 238.76) (152.606375632 241.34) (152.384673411 243.56) (152.052120079 245.45) (151.608715637 246.95) (151.082172861 247.88) (150.38935342 248.54) (149.502544535 248.96) (148.449458984 249.08) (147.424086211 248.96) (146.592702881 248.66) (145.927596217 248.12) (145.428766219 247.37) (145.06850011 246.32) (144.819085111 244.94) (144.680521223 243.2) (144.625095667 241.1) (144.625095667 233.15) (144.652808445 232.04) (144.680521223 231.14) (144.763659556 230.42) (144.846797889 229.91) (145.040787332 229.37) (145.373340664 228.59) (145.872170662 227.66) (146.48185177 226.49) (146.758979547 225.71) (146.84211788 224.84) (146.675841214 223.73) (146.177011216 222.77) (145.345627887 221.99) (144.153978447 221.36) (142.629775676 220.88) (140.717594018 220.52) (138.417433473 220.28) (135.757006818 220.22) (133.623122938 220.28) (131.766366835 220.52) (130.186738509 220.88) (128.911950737 221.39) (127.914290741 222.02) (127.193758522 222.83) (126.778066857 223.76) (126.639502969 224.84) (126.694928524 225.71) (126.916630746 226.31) (127.387747966 226.91) (128.246844073 227.72) (128.939663514 228.56) (129.327642402 229.49) (129.438493512 230.15) (129.549344623 231.17) (129.632482956 232.58) (129.743334066 234.32) (129.909610732 239) (129.965036288 243.92) (129.93732351 245.18) (129.881897955 246.2) (129.771046844 247.01) (129.632482956 247.55) (128.967376292 248.51) (127.637162965 249.65) (127.027481856 250.22) (126.584077414 250.85) (126.334662415 251.54) (126.251524082 252.29) (126.528651858 253.76) (127.387747966 254.93) (128.108280185 255.47) (129.133652958 256.07) (130.463866285 256.76) (132.098920167 257.51) (135.202751265 258.77) (138.195731251 259.82) (139.525944579 260.24) (140.662168463 260.54) (141.52126457 260.72) (142.186371234 260.78) (143.100892896 260.54) (143.849137893 259.88) (144.347967891 258.92) (144.514244557 257.81) (144.514244557 257.48) (144.486531779 256.79) (144.458819002 256.22) (144.541957335 255.38) (144.791372333 254.78) (145.179351221 254.42) (145.761319551 254.3) (146.149298439 254.39) (146.564990103 254.69) (146.980681768 255.17) (147.424086211 255.83) (149.003714537 258.02) (150.888183418 259.58) (153.10520563 260.51) (155.627068397 260.81) (157.622388388 260.66) (159.479144491 260.15) (161.169623928 259.34) (162.721539477 258.17) (164.495157247 256.1) (165.603668353 253.73) (165.99164724 252.29) (166.268775016 250.58) (166.490477238 248.54) (166.629041126 246.23))
  ((37.1934433314 194) (40.3731722648 193.94) (43.1624081713 193.79) (45.5332586918 193.52) (47.5136161854 193.13) (48.9919112159 192.56) (50.1076055785 191.66) (50.8606992732 190.49) (51.1117305048 189.17) (50.9164839914 188.12) (50.3586368101 187.01) (49.5218660381 185.57) (49.2429424475 184.58) (49.3545118837 183.74) (49.7171125516 182.66) (50.330744451 181.37) (51.195407582 179.87) (51.8369318405 178.94) (52.4505637399 178.28) (53.0363032803 177.89) (53.6220428207 177.77) (54.3472441564 177.92) (55.044553133 178.4) (55.8534315459 179.3) (56.8296641131 180.68) (57.4432960126 181.64) (57.8616813985 182.48) (58.1127126301 183.23) (58.1963897073 183.89) (58.1684973483 184.52) (58.0290355529 185) (57.6664348851 185.63) (56.9133411903 186.77) (56.3833863681 187.88) (56.2160322137 189.32) (56.3833863681 190.4) (56.8854488313 191.36) (57.6943272442 192.14) (58.8658063249 192.8) (60.3441013553 193.28) (62.1571046946 193.64) (64.3048163426 193.88) (66.7872362994 193.94) (69.5206874877 193.91) (71.7241838539 193.79) (73.3977253978 193.58) (74.5692044785 193.28) (75.6012217639 192.68) (76.4379925358 191.72) (76.9958397171 190.52) (77.1910862306 189.26) (76.9679473581 187.79) (76.3264230996 186.71) (75.1270516598 185.96) (73.3140483206 185.42) (71.4731526223 184.73) (69.9111805146 183.62) (69.0186250246 182.72) (67.8471459438 181.37) (66.3688509134 179.6) (64.5837399332 177.35) (62.4639206443 174.53) (60.7903791004 172.13) (59.5352229424 170.09) (58.7263445296 168.47) (58.2242820664 166.88) (57.8616813985 164.93) (57.638542526 162.62) (57.5548654488 159.95) (57.638542526 155.36) (57.8895737576 151.13) (58.0011431939 149.96) (58.1406049892 149) (58.3079591436 148.25) (58.5310980161 147.65) (59.2841917109 146.69) (60.5393478688 145.76) (61.6271498723 144.92) (62.4360282852 143.99) (62.8823060302 142.97) (63.0496601846 141.86) (62.8265213121 140.54) (62.1849970536 139.43) (61.0971950501 138.47) (59.5910076606 137.66) (57.610650167 137.06) (55.2397996464 136.64) (52.4226713809 136.37) (49.1592653703 136.28) (43.6086859163 136.61) (38.3928147712 137.6) (36.5240267138 138.29) (35.1851934787 139.25) (34.3763150658 140.48) (34.0973914752 141.98) (34.2647456295 143.18) (34.7668080927 144.17) (35.5756865056 144.98) (36.7192732273 145.64) (37.6118287173 146.06) (38.337030053 146.57) (38.8390925162 147.11) (39.173800825 147.74) (39.4248320566 148.55) (39.6758632882 149.63) (39.8711098016 150.92) (40.0105715969 152.48) (40.1221410332 154.28) (40.2337104695 156.32) (40.2616028285 158.6) (40.2894951876 161.12) (40.2616028285 162.68) (40.1500333923 164.03) (39.7316480063 166.22) (38.8669848753 168.32) (37.3329051267 170.96) (33.3442977804 176.69) (29.2720133569 181.85) (27.5147947358 183.59) (25.8133608328 184.67) (24.7534511884 185.15) (23.9445727755 185.57) (23.3309408761 185.93) (22.9683402082 186.2) (22.2431388725 187.34) (22.02 188.81) (22.2431388725 190.1) (22.884663131 191.18) (23.9724651346 192.08) (25.5065448831 192.77) (27.5426870949 193.31) (30.164568847 193.7) (33.4000824985 193.91) (37.1934433314 194))
  ((105.723987429 178.01) (108.792146926 177.77) (111.637167551 177.05) (114.314834021 175.82) (116.797253978 174.11) (118.415010803 172.61) (119.893305834 170.9) (121.176354351 168.98) (122.292048713 166.85) (123.240388922 164.48) (123.909805539 162.08) (124.300298566 159.59) (124.439760361 157.07) (124.328190925 154.88) (124.021374975 152.81) (123.463527794 150.77) (122.738326458 148.85) (121.762093891 146.99) (120.59061481 145.22) (119.195996857 143.54) (117.578240031 141.95) (115.904698488 140.54) (114.175372225 139.34) (112.390261245 138.32) (110.521473188 137.48) (108.624792772 136.82) (106.644435278 136.34) (104.636185425 136.07) (102.544258495 135.98) (98.6114358672 136.34) (95.069106266 137.36) (91.9172696916 139.13) (89.1559261442 141.56) (86.9803221371 144.47) (85.4462423885 147.8) (84.4979021803 151.55) (84.1910862306 155.69) (84.2747633078 158.06) (84.5815792575 160.31) (85.0557493616 162.44) (85.7251659792 164.48) (86.5619367511 166.4) (87.6218463956 168.23) (88.8491101945 169.94) (90.2716205068 171.53) (91.9172696916 173.06) (93.6187035946 174.35) (95.4317069338 175.49) (97.3283873502 176.39) (99.2808524848 177.11) (101.344887056 177.59) (103.492598704 177.92) (105.723987429 178.01))
  ((102.962643881 168.53) (101.568025928 168.2) (100.508116284 167.21) (99.8386996661 165.65) (99.6155607936 163.64) (99.6713455117 162.32) (99.810807307 160.73) (100.03394618 158.96) (100.368654488 156.95) (101.233317619 152.93) (102.237442546 149.42) (102.851074445 147.95) (103.632060499 146.87) (104.608293066 146.24) (105.723987429 146.03) (107.062820664 146.33) (108.011160872 147.2) (108.596900412 148.64) (108.792146926 150.68) (108.596900412 154.37) (108.011160872 158.51) (107.620667845 160.61) (107.1743901 162.5) (106.672327637 164.18) (106.142372815 165.65) (105.500848556 166.88) (104.775647221 167.75) (103.91098409 168.32) (102.962643881 168.53))
  ((150.992304066 175.64) (150.992304066 153.38) (151.048088784 151.7) (151.243335298 150.26) (151.550151247 149.03) (151.996428992 148.04) (152.554276174 147.26) (153.25158515 146.69) (154.060463563 146.36) (154.980911412 146.24) (155.95714398 146.42) (156.933376547 146.93) (157.74225496 147.68) (158.300102141 148.58) (158.63481045 149.87) (158.857949322 151.76) (158.997411118 154.28) (159.053195836 157.37) (159.025303477 160.49) (158.9416264 163.04) (158.830056963 165.08) (158.662702809 166.58) (158.467456295 167.45) (158.188532705 168.05) (157.686470242 168.56) (156.877591829 169.16) (156.012928698 169.82) (155.399296798 170.54) (155.008803771 171.38) (154.897234335 172.28) (155.120373208 173.45) (155.761897466 174.44) (156.821807111 175.22) (158.300102141 175.79) (161.507723434 176.63) (164.687452367 177.2) (167.839288941 177.56) (170.963233157 177.68) (172.497312905 177.41) (173.585114909 176.6) (174.226639167 175.22) (174.44977804 173.3) (174.44977804 172.61) (174.421885681 171.44) (174.366100962 169.25) (174.310316244 166.64) (174.310316244 148.55) (174.44977804 147.86) (174.812378708 147.23) (175.453902966 146.6) (176.318566097 146) (177.071659792 145.46) (177.601614614 144.77) (177.908430564 144.02) (178.02 143.12) (177.908430564 142.22) (177.573722255 141.38) (176.987982715 140.6) (176.179104302 139.85) (175.147087016 139.16) (173.891930858 138.53) (172.385743469 137.96) (170.656417207 137.42) (166.416778629 136.52) (162.288709487 136.22) (160.921983893 136.34) (160.029428403 136.67) (159.555258299 137.33) (159.332119426 138.44) (159.192657631 139.55) (158.91373404 140.36) (158.523241014 140.84) (158.02117855 140.99) (157.240192497 140.78) (156.989161265 140.6) (156.54288352 140.24) (155.929251621 139.76) (155.148265567 139.1) (153.363154587 137.87) (151.522258888 136.97) (149.625578472 136.46) (147.645220978 136.28) (144.577061481 136.55) (141.983072088 137.42) (139.891145158 138.83) (138.273388332 140.84) (137.269263406 143.06) (136.54406207 145.94) (136.097784325 149.48) (135.95832253 153.68) (135.986214889 156.8) (136.014107248 159.41) (136.014107248 160.58) (136.014107248 161.3) (135.986214889 162.95) (135.874645453 164.39) (135.707291298 165.56) (135.456260067 166.49) (134.703166372 167.96) (133.503794932 169.1) (132.415992929 169.85) (131.802361029 170.42) (131.523437439 170.99) (131.439760361 171.77) (131.690791593 173.21) (132.443885288 174.38) (133.699041446 175.28) (135.428367708 175.94) (138.803343155 176.72) (142.178318601 177.26) (145.581186407 177.56) (148.956161854 177.68) (149.848717344 177.56) (150.490241603 177.17) (150.852842271 176.54) (150.992304066 175.64))
  ((30.7520907224 79.79) (30.1163356356 79.61) (29.7495538548 79.07) (29.6517453799 78.59) (29.5783890237 77.87) (29.553936905 76.91) (29.5294847863 75.71) (29.553936905 73.85) (29.6028411424 72.2) (29.7006496173 70.76) (29.8473623297 69.56) (30.1652398731 68.57) (30.4586652977 68.18) (30.9477076722 67.73) (31.4856542841 67.16) (31.8768881837 66.53) (32.0969572522 65.81) (32.1703136084 65.03) (32.0725051335 64.07) (31.7546275901 63.26) (31.2166809782 62.63) (30.4586652977 62.12) (29.4561284301 61.73) (28.135714019 61.46) (26.546326302 61.31) (24.6390610416 61.25) (22.8540563748 61.31) (21.3135728953 61.52) (20.0176106029 61.88) (18.9417173791 62.36) (18.1103453425 62.96) (17.4990423745 63.71) (17.1567127123 64.61) (17.0344521187 65.63) (17.2545211872 66.83) (17.6213029681 67.37) (18.2815101736 68.09) (19.039525854 69.08) (19.5041161098 70.22) (19.6508288221 70.94) (19.7730894157 71.9) (19.8708978906 73.07) (19.9442542468 74.48) (19.9687063655 75.2) (19.9931584842 76.31) (20.0176106029 77.75) (20.0420627217 79.55) (20.0420627217 81.71) (20.0665148404 84.23) (20.0665148404 87.11) (20.0665148404 90.35) (20.0420627217 92.36) (19.9931584842 94.01) (19.8953500093 95.3) (19.7730894157 96.26) (19.30849916 97.61) (18.5260313608 98.54) (17.7924677991 99.17) (17.3278775434 99.74) (17.0833563562 100.37) (17.01 101.15) (17.1567127123 102.23) (17.5968508494 103.16) (18.3059622923 103.91) (19.2351428038 104.42) (20.2865839089 104.69) (21.6559025574 104.78) (22.1204928131 104.75) (22.8540563748 104.69) (23.8321411238 104.6) (25.0547470599 104.45) (25.7149542654 104.42) (26.6930390144 104.39) (27.695575882 104.42) (28.844825462 104.48) (30.1652398731 104.6) (31.6323669965 104.78) (33.2951110696 104.93) (34.3710042934 104.99) (36.4738865036 104.78) (38.381151764 104.18) (40.1172521934 103.19) (41.657735673 101.78) (42.7825331342 100.19) (43.5894530521 98.3) (44.0784954265 96.14) (44.2496602576 93.71) (44.0295911891 90.98) (43.3449318648 88.49) (42.269038641 86.45) (40.8508157551 84.95) (40.3617733806 84.41) (40.1906085496 83.78) (40.4351297368 82.94) (41.1931454172 82.31) (43.0759585589 80.81) (44.3719208512 78.71) (44.836511107 77.36) (45.2277450065 75.68) (45.5700746687 73.67) (45.8145958559 71.36) (45.9124043308 70.43) (46.0346649244 69.65) (46.3525424678 68.69) (46.9149411984 68.09) (47.9663823035 67.52) (48.3331640844 67.22) (48.6265895091 66.71) (48.895562815 65.36) (48.7733022214 64.4) (48.4065204405 63.41) (47.8441217099 62.54) (47.1350102669 61.88) (46.1813776367 61.34) (45.0810322942 60.95) (43.8095221206 60.74) (42.3912992346 60.65) (40.5329382117 60.86) (38.9435504947 61.46) (37.6475882024 62.45) (36.6450513347 63.86) (35.9359398917 65.48) (35.3246369237 67.49) (35.031211499 68.72) (34.7133339556 70.28) (34.3954564122 72.14) (34.0286746313 74.3) (33.7841534441 75.65) (33.4907280194 76.82) (33.172850476 77.75) (32.8305208139 78.47) (31.9502445399 79.4) (30.7520907224 79.79))
  ((28.1281768068 95.69) (27.7118772945 88.43) (27.7118772945 88.13) (27.795137197 87.2) (28.0865468556 86.63) (28.6693661728 86.36) (29.5852250999 86.27) (32.2495419787 86.63) (34.0812598329 87.68) (34.6640791501 88.49) (35.1220086137 89.54) (35.371788321 90.77) (35.4550482235 92.24) (35.371788321 93.65) (35.1636385649 94.85) (34.7889690038 95.9) (34.2477796378 96.74) (33.5817004181 97.4) (32.7491013935 97.85) (31.7916125152 98.15) (30.6676038319 98.24) (29.5019651974 98.09) (28.7526260753 97.7) (28.336326563 96.92) (28.1281768068 95.69))
  ((74.9926675378 75.86) (65.3340806422 75.86) (64.8450382677 75.65) (64.6983255553 75.02) (64.7961340302 74) (65.0651073362 73.04) (65.5052454732 72.08) (66.14100056 71.18) (66.8745641217 70.4) (67.6570319209 69.83) (68.43949972 69.5) (69.2708717566 69.38) (70.297860743 69.53) (71.4471103229 69.98) (72.5474556655 70.61) (73.4277319395 71.39) (74.0634870263 71.96) (74.5525294008 72.14) (75.0904760127 71.9) (75.6039705059 71.15) (75.9952044055 70.13) (76.1174649991 69.08) (75.9952044055 67.97) (75.6528747433 66.86) (75.066023894 65.78) (74.2591039761 64.73) (72.5719077842 63.11) (70.73799888 61.97) (68.7818293821 61.28) (66.7033992906 61.04) (64.6249691992 61.28) (62.7421560575 62) (61.0060556282 63.17) (59.4655721486 64.85) (58.1696098563 66.89) (57.1181687512 69.35) (56.5802221393 71.15) (56.2134403584 72.98) (55.9689191712 74.87) (55.895562815 76.79) (56.0178234086 79.34) (56.4335094269 81.77) (57.0937166324 84.05) (57.9984450252 86.21) (58.9765297741 87.89) (60.0524229979 89.36) (61.2750289341 90.59) (62.6198954639 91.61) (64.7961340302 92.6) (67.1679895464 92.93) (69.0508026881 92.72) (70.7869031174 92.09) (72.3762908344 91.04) (73.8189658391 89.57) (75.066023894 87.74) (76.0441086429 85.58) (76.7532200859 83) (76.9977412731 80.48) (76.8510285608 78.62) (76.4353425425 77.15) (75.7995874557 76.19) (74.9926675378 75.86))
  ((65.2226596476 79.5) (68.6152860855 79.5) (69.5732041386 79.7127659574) (70.2517294262 80.2978723404) (70.6508619483 81.3617021277) (70.7706017049 82.7446808511) (70.4912089395 85.4574468085) (69.6929438952 87.6382978723) (68.4955463289 89.0212765957) (66.9788427449 89.5) (65.302486152 88.914893617) (64.0252620812 87.1063829787) (63.2669102892 84.7659574468) (63.0274307759 82.4787234043) (63.1471705326 81.0957446809) (63.5063898025 80.1914893617) (64.1849150901 79.6595744681) (65.2226596476 79.5))
  ((95.9548273287 92.99) (97.6909277581 92.81) (99.2803154751 92.3) (100.72299048 91.43) (102.043404891 90.23) (103.168202352 88.64) (103.877313795 86.87) (104.268547695 84.62) (104.366356169 83.24) (104.390808288 81.68) (104.366356169 77.03) (104.390808288 74.84) (104.488616763 73.04) (104.610877357 71.69) (104.806494307 70.76) (105.026563375 70.19) (105.246632444 69.89) (105.564509987 69.71) (106.102456599 69.56) (106.591498973 69.14) (106.762663804 68.24) (106.567046855 66.71) (105.980196005 65.12) (105.075467612 63.62) (103.926218032 62.39) (102.361282434 61.37) (100.698538361 61.04) (99.6715493746 61.19) (98.7668209819 61.61) (97.959901064 62.3) (97.2752417398 63.29) (96.8595557215 63.89) (96.4683218219 64.1) (96.0037315662 63.89) (95.3924285981 63.32) (94.340987493 62.33) (93.191737913 61.61) (91.9935840956 61.19) (90.722073922 61.04) (89.4261116296 61.16) (88.2768620497 61.46) (87.2498730633 62) (86.3451446705 62.78) (85.3915120403 64.1) (84.6334963599 65.78) (84.1444539854 67.7) (83.9977412731 69.68) (84.095549748 71.24) (84.4134272914 72.74) (84.9513739033 74.12) (85.7093895837 75.41) (87.2254209446 77.12) (89.0837819675 78.35) (91.2600205339 79.1) (93.7785887624 79.37) (94.7566735113 79.46) (95.2946201232 79.73) (95.5146891917 80.33) (95.5880455479 81.41) (95.5635934292 82.94) (95.490237073 84.23) (95.3435243606 85.31) (95.1479074109 86.18) (94.8789341049 86.84) (94.5366044428 87.29) (94.1453705432 87.59) (93.6563281688 87.68) (93.0694773194 87.53) (92.5559828262 87.11) (92.0180362143 86.33) (91.3578290088 85.04) (90.4286484973 83.3) (89.4750158671 82.07) (88.5213832369 81.32) (87.5188463692 81.08) (86.6141179765 81.29) (85.8805544148 81.98) (85.415964159 83.03) (85.244799328 84.38) (85.4404162778 85.85) (86.0272671271 87.35) (86.9564476386 88.76) (88.1790535748 89.99) (90.0618667164 91.28) (91.9935840956 92.24) (93.9497535934 92.81) (95.9548273287 92.99))
  ((95.3136384378 76.33) (93.3497907384 75.9518487395) (91.7226026446 74.7753781513) (90.544294025 73.0526890756) (90.1515244851 71.0358823529) (90.4320741564 69.1031092437) (91.2737231705 67.6325210084) (92.5642516586 66.6661344538) (94.1353298181 66.33) (95.7625179119 66.7081512605) (96.9408265315 67.8005882353) (97.670255677 69.6493277311) (97.8946954141 72.2543697479) (97.7824755456 74.2291596639) (97.3897060057 75.4896638655) (96.6041669259 76.1199159664) (95.3136384378 76.33))
  ((125.91536681 86.6) (125.91536681 76.61) (125.91536681 73.64) (125.939818929 71.33) (125.988723166 69.77) (126.037627403 68.87) (126.379957066 67.88) (127.06461639 67.19) (127.700371477 66.68) (128.067153257 66.23) (128.262770207 65.72) (128.336126563 65) (128.21386597 64.01) (127.847084189 63.11) (127.284685458 62.39) (126.575574015 61.94) (125.695297741 61.64) (124.57050028 61.43) (123.201181632 61.28) (121.562889677 61.25) (119.728980773 61.31) (118.188497293 61.46) (116.941439238 61.76) (115.987806608 62.15) (115.303147284 62.66) (114.765200672 63.41) (114.42287101 64.28) (114.300610416 65.21) (114.545131604 66.38) (114.960817622 66.8) (115.669929065 67.34) (116.036710846 67.73) (116.33013627 68.33) (116.550205339 69.17) (116.672465932 70.22) (116.819178645 72.47) (116.91698712 75.14) (116.965891357 78.26) (116.990343476 81.77) (116.965891357 85.22) (116.91698712 88.01) (116.819178645 90.14) (116.696918051 91.58) (116.207875677 93.47) (115.254243046 94.82) (114.545131604 95.54) (114.080541348 96.23) (113.836020161 96.98) (113.762663804 97.88) (114.007184992 99.29) (114.740748553 100.55) (115.987806608 101.63) (117.821715512 102.65) (119.460007467 103.28) (121.489533321 103.88) (122.540974426 104.15) (123.445702819 104.33) (124.203718499 104.45) (124.790569349 104.48) (125.499680791 104.3) (126.013175285 103.7) (126.331052828 102.77) (126.428861303 101.42) (126.404409184 100.76) (126.379957066 99.77) (126.306600709 98.48) (126.208792234 96.83) (126.013175285 91.49) (125.91536681 86.6))
  ((147.46437745 86.6) (147.46437745 76.61) (147.46437745 73.64) (147.513281688 71.33) (147.537733806 69.77) (147.611090162 68.87) (147.928967706 67.88) (148.61362703 67.19) (149.249382117 66.68) (149.640616016 66.23) (149.836232966 65.72) (149.909589322 65) (149.787328729 64.01) (149.420546948 63.11) (148.858148217 62.39) (148.124584656 61.94) (147.2687605 61.64) (146.143963039 61.43) (144.774644391 61.28) (143.136352436 61.25) (141.277991413 61.31) (139.737507934 61.46) (138.490449879 61.76) (137.536817248 62.15) (136.876610043 62.66) (136.338663431 63.41) (135.97188165 64.28) (135.849621057 65.21) (136.118594363 66.38) (136.534280381 66.8) (137.243391824 67.34) (137.610173605 67.73) (137.879146911 68.33) (138.099215979 69.17) (138.221476573 70.22) (138.368189285 72.47) (138.46599776 75.14) (138.539354116 78.26) (138.563806235 81.77) (138.539354116 85.22) (138.490449879 88.01) (138.392641404 90.14) (138.27038081 91.58) (137.756886317 93.47) (136.827705805 94.82) (136.094142244 95.54) (135.654004107 96.23) (135.40948292 96.98) (135.336126563 97.88) (135.580647751 99.29) (136.289759194 100.55) (137.561269367 101.63) (139.370726153 102.65) (141.009018107 103.28) (143.06299608 103.88) (144.114437185 104.15) (145.019165578 104.33) (145.777181258 104.45) (146.364032108 104.48) (147.07314355 104.3) (147.586638044 103.7) (147.880063468 102.77) (147.977871943 101.42) (147.953419825 100.76) (147.928967706 99.77) (147.85561135 98.48) (147.782254993 96.83) (147.562185925 91.49) (147.46437745 86.6))
  ((177.302656338 77.6) (174.588471159 66.26) (174.099428785 64.25) (173.585934292 62.45) (173.072439798 60.83) (172.558945305 59.39) (171.483052081 56.93) (170.260446145 54.86) (168.842223259 53.18) (167.30173978 51.95) (165.614543588 51.23) (163.805086802 50.99) (162.362411798 51.14) (161.041997387 51.59) (159.892747807 52.37) (158.86575882 53.42) (158.230003733 54.44) (157.765413478 55.55) (157.496440172 56.81) (157.398631697 58.19) (157.667605003 60.38) (158.425620683 62.24) (158.963567295 62.96) (159.574870263 63.44) (160.21062535 63.77) (160.919736793 63.86) (161.628848236 63.77) (162.264603323 63.5) (162.827002053 63.02) (163.316044428 62.36) (163.902895277 61.16) (164.074060108 60.29) (164.318581296 58.82) (164.685363076 57.77) (165.345570282 57.44) (165.932421131 57.65) (166.421463506 58.28) (166.763793168 59.24) (166.861601643 60.38) (166.788245287 61.22) (166.592628337 62.33) (166.250298675 63.68) (165.785708419 65.27) (160.821928318 81.29) (160.455146537 82.4) (160.137268994 83.3) (159.868295688 83.99) (159.648226619 84.41) (159.012471533 85.07) (157.91212619 85.94) (157.545344409 86.3) (157.203014747 86.9) (156.909589322 88.34) (157.129658391 89.6) (157.814317715 90.65) (158.963567295 91.49) (160.552955012 92.09) (163.144879597 92.6) (166.103585962 92.75) (168.035303341 92.57) (169.526882584 92.06) (170.260446145 91.52) (170.798392757 90.83) (171.116270301 89.99) (171.214078775 88.97) (171.091818182 88.13) (170.74948852 87.14) (170.407158858 86.21) (170.284898264 85.37) (170.504967332 83.81) (170.847296995 82.7) (171.434147844 81.05) (171.800929625 80.09) (172.167711406 79.43) (172.485588949 79.01) (172.803466492 78.89) (173.121344036 79.01) (173.439221579 79.37) (173.781551241 79.94) (174.123880903 80.78) (174.637375397 82.67) (174.808540228 84.5) (174.686279634 85.79) (174.295045735 86.84) (173.708194885 88.13) (173.512577935 89.24) (173.61038641 89.99) (173.854907598 90.65) (174.295045735 91.25) (174.906348703 91.76) (176.544640657 92.48) (178.647522867 92.72) (180.554788128 92.51) (181.924106776 91.94) (182.731026694 90.95) (183 89.54) (182.902191525 88.49) (182.559861863 87.68) (181.948558895 87.02) (180.946022027 86.36) (180.065745753 85.61) (179.381086429 84.5) (178.916496173 83.27) (178.427453799 81.71) (177.865055068 79.82) (177.302656338 77.6))
))
(setq ast:velvet-arcs '(
  ((107.803914653 -2450.66165448) 2755.66165448 1.60520643877 -0.0631534779527)
  ((109.249918632 -2291.70462567) 2593.90462567 1.60791103743 -0.0670933489092)
  ((110.690439376 -2151.63309415) 2451.03309415 1.61066372914 -0.071006065483)
  ((112.124622962 -2027.46267979) 2324.06267979 1.61346071022 -0.0748874111159)
  ((113.551619226 -1916.80768179) 2210.60768179 1.61629798929 -0.0787332040864)
  ((114.970582261 -1817.73840779) 2108.73840779 1.61917139493 -0.0825393018008)
  ((116.380670924 -1728.67745102) 2016.87745102 1.6220765839 -0.0863016049918)
  ((117.781049333 -1648.323052) 1933.723052 1.62500904998 -0.0900160618204)
  ((119.17088736 -1575.59163853) 1858.19163853 1.62796413326 -0.0936786718821)
  ((120.549361128 -1509.57417037) 1789.37417037 1.63093703012 -0.0972854901157)
  ((121.915653495 -1449.50256901) 1726.50256901 1.63392280362 -0.0179239795854)
  ((121.915653495 -1449.50256901) 1726.50256901 1.6046954146 -0.0716052415995)
  ((123.26895454 -1394.72361624) 1668.92361624 1.6369163944 -0.0158455707467)
  ((123.26895454 -1394.72361624) 1668.92361624 1.60101138669 -0.0684112626492)
  ((124.608462043 -1344.67845318) 1616.07845318 1.63991263207 -0.0144144168549)
  ((124.608462043 -1344.67845318) 1616.07845318 1.60162178016 -0.0694418009423)
  ((125.93338196 -1298.88632709) 1567.48632709 1.642906247 -0.0134260463908)
  ((125.93338196 -1298.88632709) 1567.48632709 1.602657422 -0.0708292666362)
  ((127.242928897 -1256.93159439) 1522.73159439 1.6458918826 -0.0126388835133)
  ((127.242928897 -1256.93159439) 1522.73159439 1.6205254689 -0.00315588898491)
  ((127.242928897 -1256.93159439) 1522.73159439 1.60406040937 -0.0725175005809)
  ((128.536326571 -1218.45324433) 1481.45324433 1.64886410791 -0.0120803757138)
  ((128.536326571 -1218.45324433) 1481.45324433 1.62451019583 -0.00780610031947)
  ((128.536326571 -1218.45324433) 1481.45324433 1.60555725962 -0.0742349151377)
  ((129.812808271 -1183.13639169) 1443.33639169 1.65181743058 -0.01167274025)
  ((129.812808271 -1183.13639169) 1443.33639169 1.62744044787 -0.00999024778567)
  ((129.812808271 -1183.13639169) 1443.33639169 1.60736061441 -0.010085862997)
  ((129.812808271 -1183.13639169) 1443.33639169 1.58438526698 -0.0176678285803)
  ((129.812808271 -1183.13639169) 1443.33639169 1.56027385117 -0.00322194073877)
  ((129.812808271 -1183.13639169) 1443.33639169 1.54821672504 -0.0170522992577)
  ((131.071617315 -1150.70532099) 1408.10532099 1.65474631021 -0.0115401343404)
  ((131.071617315 -1150.70532099) 1408.10532099 1.62996820068 -0.0114146672772)
  ((131.071617315 -1150.70532099) 1408.10532099 1.60949031622 -0.00746140594061)
  ((131.071617315 -1150.70532099) 1408.10532099 1.58327555909 -0.0111855664064)
  ((131.071617315 -1150.70532099) 1408.10532099 1.56037193004 -0.000958792135884)
  ((131.071617315 -1150.70532099) 1408.10532099 1.54652133887 -0.0154543545115)
  ((132.312007498 -1120.91776256) 1375.51776256 1.65764517193 -0.011597420042)
  ((132.312007498 -1120.91776256) 1375.51776256 1.6321659343 -0.0127782272691)
  ((132.312007498 -1120.91776256) 1375.51776256 1.61240139936 -0.00709339139824)
  ((132.312007498 -1120.91776256) 1375.51776256 1.58316435408 -0.00752473574642)
  ((132.312007498 -1120.91776256) 1375.51776256 1.54575732534 -0.0147295946845)
  ((133.533243531 -1093.56015447) 1345.36015447 1.66050842028 -0.0118600670924)
  ((133.533243531 -1093.56015447) 1345.36015447 1.63411778141 -0.0263465395601)
  ((133.533243531 -1093.56015447) 1345.36015447 1.59840080117 -0.0024537289768)
  ((133.533243531 -1093.56015447) 1345.36015447 1.58368040325 -0.00657847886648)
  ((133.533243531 -1093.56015447) 1345.36015447 1.54565784002 -0.0146135755191)
  ((134.734601482 -1068.44369863) 1317.44369863 1.66333045333 -0.0122283945861)
  ((134.734601482 -1068.44369863) 1317.44369863 1.63580473111 -0.026451016962)
  ((134.734601482 -1068.44369863) 1317.44369863 1.60137894819 -0.00432831165239)
  ((134.734601482 -1068.44369863) 1317.44369863 1.58452379727 -0.0076288028126)
  ((134.734601482 -1068.44369863) 1317.44369863 1.54580943446 -0.0146953483323)
  ((135.9153692 -1045.40106104) 1291.60106104 1.666105677 -0.0128255742798)
  ((135.9153692 -1045.40106104) 1291.60106104 1.63720879255 -0.0279116816515)
  ((135.9153692 -1045.40106104) 1291.60106104 1.60546208984 -0.00697149851351)
  ((135.9153692 -1045.40106104) 1291.60106104 1.58571276208 -0.00929131795378)
  ((135.9153692 -1045.40106104) 1291.60106104 1.56271740473 -0.00325193263878)
  ((135.9153692 -1045.40106104) 1291.60106104 1.5461076895 -0.014873082224)
  ((137.074846742 -1024.28359791) 1267.68359791 1.6688285195 -0.0136643892583)
  ((137.074846742 -1024.28359791) 1267.68359791 1.63807587228 -0.0292681285787)
  ((137.074846742 -1024.28359791) 1267.68359791 1.58690896766 -0.00958506133221)
  ((137.074846742 -1024.28359791) 1267.68359791 1.56383463339 -0.00414158385495)
  ((137.074846742 -1024.28359791) 1267.68359791 1.54643835087 -0.0150351882365)
  ((138.212346784 -1004.9590134) 1245.5590134 1.67149344593 -0.01475653795)
  ((138.212346784 -1004.9590134) 1245.5590134 1.6382568518 -0.0114625409152)
  ((138.212346784 -1004.9590134) 1245.5590134 1.62160851387 -0.00807752240918)
  ((138.212346784 -1004.9590134) 1245.5590134 1.58810857269 -0.00975544908997)
  ((138.212346784 -1004.9590134) 1245.5590134 1.56462423704 -0.00445599152337)
  ((138.212346784 -1004.9590134) 1245.5590134 1.54679865045 -0.0151816291596)
  ((139.32719503 -987.309373908) 1225.10937391 1.67409497297 -0.0161125820026)
  ((139.32719503 -987.309373908) 1225.10937391 1.62263303049 -0.0058840668545)
  ((139.32719503 -987.309373908) 1225.10937391 1.58930772725 -0.00979599068912)
  ((139.32719503 -987.309373908) 1225.10937391 1.565431225 -0.00453034352028)
  ((139.32719503 -987.309373908) 1225.10937391 1.54730826005 -0.0154348616464)
  ((140.418730612 -971.229418352) 1206.22941835 1.67662768358 -0.0177418973016)
  ((140.418730612 -971.229418352) 1206.22941835 1.62447585173 -0.00522971001062)
  ((140.418730612 -971.229418352) 1206.22941835 1.60754614178 -0.00497710413192)
  ((140.418730612 -971.229418352) 1206.22941835 1.59025382897 -0.00957635984577)
  ((140.418730612 -971.229418352) 1206.22941835 1.5662521761 -0.00460122661993)
  ((140.418730612 -971.229418352) 1206.22941835 1.5477213305 -0.0155518637124)
  ((141.486306483 -956.625115582) 1188.82511558 1.67908624174 -0.0197793000879)
  ((141.486306483 -956.625115582) 1188.82511558 1.62679370723 -0.00568591288695)
  ((141.486306483 -956.625115582) 1188.82511558 1.60898305279 -0.00479772637895)
  ((141.486306483 -956.625115582) 1188.82511558 1.58992251486 -0.00807614071799)
  ((141.486306483 -956.625115582) 1188.82511558 1.56708366662 -0.00441620573066)
  ((141.486306483 -956.625115582) 1188.82511558 1.54815549202 -0.0156531233362)
  ((142.529289795 -943.41242912) 1172.81242912 1.68146540709 -0.0223652512025)
  ((142.529289795 -943.41242912) 1172.81242912 1.62960286121 -0.00730128757132)
  ((142.529289795 -943.41242912) 1172.81242912 1.58966601349 -0.00639568077359)
  ((142.529289795 -943.41242912) 1172.81242912 1.56753858765 -0.00383698444399)
  ((142.529289795 -943.41242912) 1172.81242912 1.54796826426 -0.0150990368736)
  ((143.547062282 -931.516256784) 1158.11625678 1.68376004954 -0.0257747666425)
  ((143.547062282 -931.516256784) 1158.11625678 1.63330663164 -0.0103787465535)
  ((143.547062282 -931.516256784) 1158.11625678 1.59130266762 -0.00505212835057)
  ((143.547062282 -931.516256784) 1158.11625678 1.56721037712 -0.00129521845361)
  ((143.547062282 -931.516256784) 1158.11625678 1.54700291446 -0.0137357556304)
  ((144.539020622 -920.86951856) 1144.66951856 1.68596516371 -0.0310813271467)
  ((144.539020622 -920.86951856) 1144.66951856 1.64174005472 -0.0189060880173)
  ((144.539020622 -920.86951856) 1144.66951856 1.593852203 -0.00655340305671)
  ((144.539020622 -920.86951856) 1144.66951856 1.56790380285 -0.000786257401454)
  ((144.539020622 -920.86951856) 1144.66951856 1.54772126199 -0.0140279788921)
  ((145.504576794 -911.412370782) 1132.41237078 1.6880758832 -0.0674055092594)
  ((145.504576794 -911.412370782) 1132.41237078 1.61205146411 -0.00556747112248)
  ((145.504576794 -911.412370782) 1132.41237078 1.5977372787 -0.0111292888338)
  ((145.504576794 -911.412370782) 1132.41237078 1.57044714021 -0.00370890738512)
  ((145.504576794 -911.412370782) 1132.41237078 1.55017921082 -0.0160344750358)
  ((146.443158428 -903.091528493) 1121.29152849 1.69008749458 -0.155468815473)
  ((147.354209146 -895.859680972) 1111.25968097 1.69199545119 -0.156883138318)
  ((148.237188887 -889.674987943) 1102.27498794 1.69379538652 -0.158172501372)
  ((149.091574233 -884.500646083) 1094.30064608 1.69548312721 -0.159335424617)
  ((149.916858715 -880.304517196) 1087.3045172 1.69705470572 -0.160370565147)
  ((150.712553115 -877.05881086) 1081.25881086 1.69850637232 -0.1612767196)
  ((151.478185754 -874.739815588) 1076.13981559 1.69983460678 -0.0120786148475)
  ((151.478185754 -874.739815588) 1076.13981559 1.67919908706 -0.141417306742)
  ((152.213302776 -873.32767358) 1071.92767358 1.70103612924 -0.00761729782018)
  ((152.213302776 -873.32767358) 1071.92767358 1.66695212619 -0.0132068899113)
  ((152.213302776 -873.32767358) 1071.92767358 1.65262194761 -0.114283786586)
  ((152.917468413 -872.806195033) 1068.60619503 1.70210791066 -0.00750055635907)
  ((152.917468413 -872.806195033) 1068.60619503 1.66537567833 -0.00338346190516)
  ((152.917468413 -872.806195033) 1068.60619503 1.64213421633 -0.103237679008)
  ((153.590265244 -873.162708763) 1066.16270876 1.7030471824 -0.00921998295949)
  ((153.590265244 -873.162708763) 1066.16270876 1.66608566782 -0.00282627483158)
  ((153.590265244 -873.162708763) 1066.16270876 1.64152015553 -0.102065391151)
  ((154.231294444 -874.387946553) 1064.58794655 1.70385144525 -0.0132092219923)
  ((154.231294444 -874.387946553) 1064.58794655 1.66824757462 -0.00523682102921)
  ((154.231294444 -874.387946553) 1064.58794655 1.64236987232 -0.1023590549)
  ((154.840176018 -876.475959268) 1063.87595927 1.70451847757 -0.0153492615945)
  ((154.840176018 -876.475959268) 1063.87595927 1.66832138842 -0.00524036164611)
  ((154.840176018 -876.475959268) 1063.87595927 1.64723318784 -0.106670389296)
  ((155.41654903 -879.424063329) 1064.02406333 1.7050463427 -0.017335593858)
  ((155.41654903 -879.424063329) 1064.02406333 1.66743561339 -0.00184109326009)
  ((155.41654903 -879.424063329) 1064.02406333 1.65200830958 -0.110899366592)
  ((155.960071812 -883.232816644) 1065.03281664 1.70543339552 -0.0191634413824)
  ((155.960071812 -883.232816644) 1065.03281664 1.65470444384 -0.113056818979)
  ((156.470422172 -887.90602361) 1066.90602361 1.70567828808 -0.0208287440754)
  ((156.470422172 -887.90602361) 1066.90602361 1.65729453388 -0.0303058467448)
  ((156.470422172 -887.90602361) 1066.90602361 1.6123493578 -0.0701719956305)
  ((156.94729758 -893.450769259) 1069.65076926 1.70577997449 -0.0224692919084)
  ((156.94729758 -893.450769259) 1069.65076926 1.65949035486 -0.0274232862233)
  ((156.94729758 -893.450769259) 1069.65076926 1.60819790259 -0.0145909406232)
  ((156.94729758 -893.450769259) 1069.65076926 1.57537475074 -0.00392653114536)
  ((156.94729758 -893.450769259) 1069.65076926 1.5537780797 -0.011081258365)
  ((157.39041535 -899.877483115) 1073.27748311 1.70573771472 -0.0236590987469)
  ((157.39041535 -899.877483115) 1073.27748311 1.6614285565 -0.026354433797)
  ((157.39041535 -899.877483115) 1073.27748311 1.60582743981 -0.00992740441926)
  ((157.39041535 -899.877483115) 1073.27748311 1.57563238798 -0.00153735994373)
  ((157.39041535 -899.877483115) 1073.27748311 1.55382917834 -0.0106243573491)
  ((157.799512809 -907.200033838) 1077.80003384 1.70555107756 -0.024259578585)
  ((157.799512809 -907.200033838) 1077.80003384 1.66226684946 -0.024990398295)
  ((157.799512809 -907.200033838) 1077.80003384 1.60411062723 -0.00807548076415)
  ((157.799512809 -907.200033838) 1077.80003384 1.57599166714 -0.001670084676)
  ((157.799512809 -907.200033838) 1077.80003384 1.55428000099 -0.0105796657609)
  ((158.174347447 -915.435856245) 1083.23585625 1.70521994262 -0.0242763522744)
  ((158.174347447 -915.435856245) 1083.23585625 1.66257120891 -0.0240329794194)
  ((158.174347447 -915.435856245) 1083.23585625 1.62327837984 -0.00277309999977)
  ((158.174347447 -915.435856245) 1083.23585625 1.60290412939 -0.00928129206999)
  ((158.174347447 -915.435856245) 1083.23585625 1.57631163327 -0.00415424748684)
  ((158.174347447 -915.435856245) 1083.23585625 1.55470896769 -0.0105264715955)
  ((158.514697067 -924.606112873) 1089.60611287 1.70474450139 -0.0241332205075)
  ((158.514697067 -924.606112873) 1089.60611287 1.66248507302 -0.023064524555)
  ((158.514697067 -924.606112873) 1089.60611287 1.62383548357 -0.00441096307562)
  ((158.514697067 -924.606112873) 1089.60611287 1.60206473491 -0.00936452450371)
  ((158.514697067 -924.606112873) 1089.60611287 1.57659175355 -0.00495595167602)
  ((158.514697067 -924.606112873) 1089.60611287 1.55525310924 -0.0106025137163)
  ((158.820359916 -934.73589289) 1096.93589289 1.70412525727 -0.0238328103096)
  ((158.820359916 -934.73589289) 1096.93589289 1.66215051367 -0.02236165458)
  ((158.820359916 -934.73589289) 1096.93589289 1.62348591351 -0.00479212308168)
  ((158.820359916 -934.73589289) 1096.93589289 1.60145046628 -0.00875470110773)
  ((158.820359916 -934.73589289) 1096.93589289 1.57683168415 -0.00505958466487)
  ((158.820359916 -934.73589289) 1096.93589289 1.55563566221 -0.0105315756767)
  ((159.0911548 -945.854451867) 1105.25445187 1.70336302469 -0.0235149691479)
  ((159.0911548 -945.854451867) 1105.25445187 1.6615707932 -0.0219203924548)
  ((159.0911548 -945.854451867) 1105.25445187 1.62292662821 -0.00489179419461)
  ((159.0911548 -945.854451867) 1105.25445187 1.60119324416 -0.00841726305847)
  ((159.0911548 -945.854451867) 1105.25445187 1.57703127065 -0.00515722366771)
  ((159.0911548 -945.854451867) 1105.25445187 1.55599480981 -0.0104522260385)
  ((159.326921194 -957.995496724) 1114.59549672 1.7024589273 -0.0230448722275)
  ((159.326921194 -957.995496724) 1114.59549672 1.66088523481 -0.021600756785)
  ((159.326921194 -957.995496724) 1114.59549672 1.62229688709 -0.0047159266595)
  ((159.326921194 -957.995496724) 1114.59549672 1.60101540396 -0.00821207898585)
  ((159.326921194 -957.995496724) 1114.59549672 1.57719054764 -0.0051140061058)
  ((159.326921194 -957.995496724) 1114.59549672 1.5563304141 -0.0103645506794)
  ((159.52751934 -971.197521117) 1124.99752112 1.70141439515 -0.0216221255668)
  ((159.52751934 -971.197521117) 1124.99752112 1.65996130936 -0.0213996300503)
  ((159.52751934 -971.197521117) 1124.99752112 1.6213312951 -0.0042716814902)
  ((159.52751934 -971.197521117) 1124.99752112 1.60118108608 -0.00840292343318)
  ((159.52751934 -971.197521117) 1124.99752112 1.57730973773 -0.00493338960093)
  ((159.52751934 -971.197521117) 1124.99752112 1.5566425069 -0.0102686444712)
  ((159.692830325 -985.504197634) 1136.50419763 1.70023116097 -0.0179480984532)
  ((159.692830325 -985.504197634) 1136.50419763 1.65761230682 -0.020253375705)
  ((159.692830325 -985.504197634) 1136.50419763 1.6203041178 -0.00356762309854)
  ((159.692830325 -985.504197634) 1136.50419763 1.6016791069 -0.0089780470121)
  ((159.692830325 -985.504197634) 1136.50419763 1.57725726326 -0.00461947251452)
  ((159.692830325 -985.504197634) 1136.50419763 1.55693128822 -0.0101646111835)
  ((159.822756156 -1000.96483444) 1149.16483444 1.69891125555 -0.0174850862543)
  ((159.822756156 -1000.96483444) 1149.16483444 1.65453992614 -0.0185869550687)
  ((159.822756156 -1000.96483444) 1149.16483444 1.60249661559 -0.0101849561669)
  ((159.822756156 -1000.96483444) 1149.16483444 1.5763854202 -0.00274114637045)
  ((159.822756156 -1000.96483444) 1149.16483444 1.55693604032 -0.00979147961359)
  ((159.917219814 -1017.6349056) 1163.0349056 1.69745700221 -0.0183117078391)
  ((159.917219814 -1017.6349056) 1163.0349056 1.65323217844 -0.0192683006486)
  ((159.917219814 -1017.6349056) 1163.0349056 1.60361913688 -0.0118698681265)
  ((159.917219814 -1017.6349056) 1163.0349056 1.5546028289 -0.00709490752354)
  ((159.976165302 -1035.57666612) 1178.17666612 1.69587101043 -0.0220418951629)
  ((159.976165302 -1035.57666612) 1178.17666612 1.65324251321 -0.0218271807941)
  ((159.976165302 -1035.57666612) 1178.17666612 1.60541279077 -0.0145195126345)
  ((159.976165302 -1035.57666612) 1178.17666612 1.55447900499 -0.00662168692651)
  ((159.999557677 -1054.85986502) 1194.65986502 1.69415616862 -0.0661998595288)
  ((159.999557677 -1054.85986502) 1194.65986502 1.6078442624 -0.0184645411846)
  ((159.999557677 -1054.85986502) 1194.65986502 1.55597948184 -0.00778602494175)
  ((159.987383074 -1075.56257243) 1212.56257243 1.69231563613 -0.0701695942024)
  ((159.987383074 -1075.56257243) 1212.56257243 1.61236275542 -0.0257419389562)
  ((159.987383074 -1075.56257243) 1212.56257243 1.57561043351 -0.00346375696021)
  ((159.987383074 -1075.56257243) 1212.56257243 1.5601470941 -0.0116299076429)
  ((159.93964871 -1097.77214011) 1231.97214011 1.69035283449 -0.141523341867)
  ((159.856382879 -1121.58631881) 1252.98631881 1.68827143791 -0.139139945124)
  ((159.737634942 -1147.11456091) 1275.71456091 1.68607536312 -0.136650933608)
  ((159.583475291 -1174.4795433) 1300.2795433 1.68376875862 -0.134059094871)
  ((159.393995309 -1203.81895297) 1326.81895297 1.68135599324 -0.131367325822)
  ((159.169307319 -1235.28758809) 1355.48758809 1.67884164426 -0.128578628625)
  ((158.909544511 -1269.05983959) 1386.45983959 1.67623048499 -0.125696106545)
  ((158.614860871 -1305.33263449) 1419.93263449 1.67352747193 -0.122722959763)
  ((158.285431082 -1344.32894281) 1456.12894281 1.67073773146 -0.00341589399427)
  ((158.285431082 -1344.32894281) 1456.12894281 1.66276906197 -0.111693811678)
  ((157.921450428 -1386.30197619) 1495.30197619 1.66786654627 -0.00201557676445)
  ((157.921450428 -1386.30197619) 1495.30197619 1.64943771348 -0.0980892193744)
  ((157.52313467 -1431.54024158) 1537.74024158 1.66491934143 -0.00195940843816)
  ((157.52313467 -1431.54024158) 1537.74024158 1.64534029992 -0.0937140969426)
  ((157.090719926 -1480.37365848) 1583.77365848 1.66190167019 -0.00323309558104)
  ((157.090719926 -1480.37365848) 1583.77365848 1.64194650094 -0.0450445398484)
  ((157.090719926 -1480.37365848) 1583.77365848 1.58951266948 -0.00672525107143)
  ((157.090719926 -1480.37365848) 1583.77365848 1.57596799788 -0.0240576135251)
  ((156.624462525 -1533.18100881) 1633.78100881 1.65881919964 -0.00350186529944)
  ((156.624462525 -1533.18100881) 1633.78100881 1.64877712482 -0.00248622974169)
  ((156.624462525 -1533.18100881) 1633.78100881 1.63911102425 -0.0416406022264)
  ((156.624462525 -1533.18100881) 1633.78100881 1.58856247127 -0.00440749265375)
  ((156.624462525 -1533.18100881) 1633.78100881 1.57534068619 -0.0231376026543)
  ((156.124638859 -1590.39906946) 1688.19906946 1.65567769607 -0.003477244575)
  ((156.124638859 -1590.39906946) 1688.19906946 1.64605079235 -0.00294011929822)
  ((156.124638859 -1590.39906946) 1688.19906946 1.63643087142 -0.0398499894333)
  ((156.124638859 -1590.39906946) 1688.19906946 1.5877824858 -0.00399879535894)
  ((156.124638859 -1590.39906946) 1688.19906946 1.57498698161 -0.0224806084054)
  ((155.591545217 -1652.5338867) 1747.5338867 1.65248301031 -0.00335831905355)
  ((155.591545217 -1652.5338867) 1747.5338867 1.64327125453 -0.00292577319774)
  ((155.591545217 -1652.5338867) 1747.5338867 1.63397964851 -0.00954402531064)
  ((155.591545217 -1652.5338867) 1747.5338867 1.6189350397 -0.0126289089903)
  ((155.591545217 -1652.5338867) 1747.5338867 1.60433074275 -0.00970341199652)
  ((155.591545217 -1652.5338867) 1747.5338867 1.58698644559 -0.00446387130923)
  ((155.591545217 -1652.5338867) 1747.5338867 1.57462547232 -0.0218031294634)
  ((155.02549761 -1720.17480067) 1812.37480067 1.64924106295 -0.00323735972254)
  ((155.02549761 -1720.17480067) 1812.37480067 1.64044390922 -0.00190808021239)
  ((155.02549761 -1720.17480067) 1812.37480067 1.63173506914 -0.0077925418446)
  ((155.02549761 -1720.17480067) 1812.37480067 1.61515904221 -0.00712367670131)
  ((155.02549761 -1720.17480067) 1812.37480067 1.59983717169 -0.00720284352899)
  ((155.02549761 -1720.17480067) 1812.37480067 1.58609480652 -0.00529734763347)
  ((155.02549761 -1720.17480067) 1812.37480067 1.5742589164 -0.00504863218238)
  ((155.02549761 -1720.17480067) 1812.37480067 1.56184413926 -0.00124152203182)
  ((155.02549761 -1720.17480067) 1812.37480067 1.55513970784 -0.00198661979003)
  ((154.426831585 -1794.01203436) 1883.41203436 1.64595782949 -0.0031144988737)
  ((154.426831585 -1794.01203436) 1883.41203436 1.62975376566 -0.00717885845638)
  ((154.426831585 -1794.01203436) 1883.41203436 1.61794996987 -0.00143511553441)
  ((154.426831585 -1794.01203436) 1883.41203436 1.61228977233 -0.00470252494871)
  ((154.426831585 -1794.01203436) 1883.41203436 1.59738781754 -0.00597487498077)
  ((154.426831585 -1794.01203436) 1883.41203436 1.58527950133 -0.00533643899418)
  ((154.426831585 -1794.01203436) 1883.41203436 1.57381045226 -0.00382285375176)
  ((154.426831585 -1794.01203436) 1883.41203436 1.5550141178 -0.00151341822872)
  ((153.795902022 -1874.858949) 1961.458949 1.64263932549 -0.00298987010791)
  ((153.795902022 -1874.858949) 1961.458949 1.62792566238 -0.00719885372826)
  ((153.795902022 -1874.858949) 1961.458949 1.61636283116 -0.00252611109456)
  ((153.795902022 -1874.858949) 1961.458949 1.60978020077 -0.0034437081132)
  ((153.795902022 -1874.858949) 1961.458949 1.601822041 -0.000535569141185)
  ((153.795902022 -1874.858949) 1961.458949 1.59554874876 -0.00535446916654)
  ((153.795902022 -1874.858949) 1961.458949 1.58438148067 -0.00520053041989)
  ((153.795902022 -1874.858949) 1961.458949 1.5734453285 -0.00382368777613)
  ((153.795902022 -1874.858949) 1961.458949 1.56159177376 -0.000688294585316)
  ((153.795902022 -1874.858949) 1961.458949 1.55593230348 -0.00206505086109)
  ((153.133082929 -1963.68047559) 2047.48047559 1.63929159176 -0.00286360821557)
  ((153.133082929 -1963.68047559) 2047.48047559 1.62395157224 -0.00528151873232)
  ((153.133082929 -1963.68047559) 2047.48047559 1.61419648489 -0.00256640357427)
  ((153.133082929 -1963.68047559) 2047.48047559 1.6075243882 -0.0030788596198)
  ((153.133082929 -1963.68047559) 2047.48047559 1.60085392689 -0.00131926402869)
  ((153.133082929 -1963.68047559) 2047.48047559 1.59403824178 -0.0049828103597)
  ((153.133082929 -1963.68047559) 2047.48047559 1.58348693884 -0.00498199677975)
  ((153.133082929 -1963.68047559) 2047.48047559 1.57301030963 -0.00490847678348)
  ((153.133082929 -1963.68047559) 2047.48047559 1.56165476086 -0.000805905220046)
  ((153.133082929 -1963.68047559) 2047.48047559 1.55747863052 -0.00322383463654)
  ((152.438767217 -2061.62981722) 2142.62981722 1.63592067962 -0.0027358490638)
  ((152.438767217 -2061.62981722) 2142.62981722 1.62764439339 -0.000560956682525)
  ((152.438767217 -2061.62981722) 2142.62981722 1.62063366442 -0.00427531909228)
  ((152.438767217 -2061.62981722) 2142.62981722 1.60549839662 -0.00420268181994)
  ((152.438767217 -2061.62981722) 2142.62981722 1.60087547748 -0.00126068037706)
  ((152.438767217 -2061.62981722) 2142.62981722 1.5926818201 -0.00476141519625)
  ((152.438767217 -2061.62981722) 2142.62981722 1.58259927763 -0.00476072085443)
  ((152.438767217 -2061.62981722) 2142.62981722 1.57258794252 -0.00518055702558)
  ((152.438767217 -2061.62981722) 2142.62981722 1.56131660387 -7.00105957803e-05)
  ((152.438767217 -2061.62981722) 2142.62981722 1.55823608883 -0.00357074807907)
  ((151.713366467 -2170.09637065) 2248.29637065 1.6325326362 -0.00253989537268)
  ((151.713366467 -2170.09637065) 2248.29637065 1.62464682228 -0.000868562240179)
  ((151.713366467 -2170.09637065) 2248.29637065 1.617632617 -0.00367316552231)
  ((151.713366467 -2170.09637065) 2248.29637065 1.60374428208 -0.00360447795351)
  ((151.713366467 -2170.09637065) 2248.29637065 1.59133036819 -0.00453752920892)
  ((151.713366467 -2170.09637065) 2248.29637065 1.58172186823 -0.00453694233215)
  ((151.713366467 -2170.09637065) 2248.29637065 1.57218109417 -0.00533738536045)
  ((151.713366467 -2170.09637065) 2248.29637065 1.55883737211 -0.00373652160214)
  ((150.957310687 -2290.76908096) 2366.16908096 1.62913348995 -0.00234940145573)
  ((150.957310687 -2290.76908096) 2366.16908096 1.62157839037 -0.000952108680555)
  ((150.957310687 -2290.76908096) 2366.16908096 1.61478763818 -0.00342631833331)
  ((150.957310687 -2290.76908096) 2366.16908096 1.60666676039 -0.00748432586827)
  ((150.957310687 -2290.76908096) 2366.16908096 1.59506041874 -0.00120481592115)
  ((150.957310687 -2290.76908096) 2366.16908096 1.58998772715 -0.00431139442216)
  ((150.957310687 -2290.76908096) 2366.16908096 1.58085803903 -0.00424750888489)
  ((150.957310687 -2290.76908096) 2366.16908096 1.57179258319 -0.00538847114005)
  ((150.957310687 -2290.76908096) 2366.16908096 1.55936718664 -0.00380395690768)
  ((150.171048058 -2425.72135478) 2498.32135478 1.62572923626 -0.00180384206145)
  ((150.171048058 -2425.72135478) 2498.32135478 1.61851488248 -0.00102182377904)
  ((150.171048058 -2425.72135478) 2498.32135478 1.6120841907 -0.0033648979271)
  ((150.171048058 -2425.72135478) 2498.32135478 1.6037928851 -0.00150178870434)
  ((150.171048058 -2425.72135478) 2498.32135478 1.60018871082 -0.00246262994343)
  ((150.171048058 -2425.72135478) 2498.32135478 1.59424263592 -0.00204188445684)
  ((150.171048058 -2425.72135478) 2498.32135478 1.58859763837 -0.0039631592615)
  ((150.171048058 -2425.72135478) 2498.32135478 1.58001106365 -0.00402280815494)
  ((150.171048058 -2425.72135478) 2498.32135478 1.57136512797 -0.00540364717694)
  ((150.171048058 -2425.72135478) 2498.32135478 1.55995725594 -0.00390294217543)
  ((149.355044667 -2577.52660316) 2647.32660316 1.62232582334 -0.00113469191483)
  ((149.355044667 -2577.52660316) 2647.32660316 1.61483801503 -0.000510437659925)
  ((149.355044667 -2577.52660316) 2647.32660316 1.60860007959 -0.00266483685347)
  ((149.355044667 -2577.52660316) 2647.32660316 1.5979988358 -0.00209717219204)
  ((149.355044667 -2577.52660316) 2647.32660316 1.59255774883 -0.00170019996916)
  ((149.355044667 -2577.52660316) 2647.32660316 1.58649395598 -0.00289000220816)
  ((149.355044667 -2577.52660316) 2647.32660316 1.57918414907 -0.0036830417586)
  ((149.355044667 -2577.52660316) 2647.32660316 1.57102487611 -0.0054394733234)
  ((149.355044667 -2577.52660316) 2647.32660316 1.56048575955 -0.00390990109485)
  ((148.509784229 -2749.41812625) 2816.41812625 1.61892913819 -0.00111970875989)
  ((148.509784229 -2749.41812625) 2816.41812625 1.61167869953 -0.00053303097671)
  ((148.509784229 -2749.41812625) 2816.41812625 1.60576267279 -0.00266446460893)
  ((148.509784229 -2749.41812625) 2816.41812625 1.59633145557 -0.00239737165913)
  ((148.509784229 -2749.41812625) 2816.41812625 1.58525128346 -0.00197076717805)
  ((148.509784229 -2749.41812625) 2816.41812625 1.57774129753 -0.00218366247301)
  ((148.509784229 -2749.41812625) 2816.41812625 1.57007192585 -0.00479335030235)
  ((148.509784229 -2749.41812625) 2816.41812625 1.56107097838 -0.00394144830798)
  ((147.635767805 -2945.51454668) 3009.71454668 1.61554499303 -0.00174603204335)
  ((147.635767805 -2945.51454668) 3009.71454668 1.60916012738 -0.00139647175752)
  ((147.635767805 -2945.51454668) 3009.71454668 1.60347493151 -0.00344051462283)
  ((147.635767805 -2945.51454668) 3009.71454668 1.59509862064 -0.00329019444603)
  ((147.635767805 -2945.51454668) 3009.71454668 1.58443118774 -0.00219307181661)
  ((147.635767805 -2945.51454668) 3009.71454668 1.57685533309 -0.00179421422976)
  ((147.635767805 -2945.51454668) 3009.71454668 1.56967853544 -0.00254177722352)
  ((147.635767805 -2945.51454668) 3009.71454668 1.56559174587 -0.000498393552048)
  ((147.635767805 -2945.51454668) 3009.71454668 1.56160455086 -0.00388765533549)
  ((146.733513501 -3171.14444039) 3232.54444039 1.61217911183 -0.00863693052757)
  ((146.733513501 -3171.14444039) 3232.54444039 1.60224222561 -0.00580275628382)
  ((146.733513501 -3171.14444039) 3232.54444039 1.59453636288 -0.00524472282592)
  ((146.733513501 -3171.14444039) 3232.54444039 1.58701754633 -0.00102099368171)
  ((146.733513501 -3171.14444039) 3232.54444039 1.58400101886 -0.00348046105542)
  ((146.733513501 -3171.14444039) 3232.54444039 1.57666898314 -0.00273781000809)
  ((146.733513501 -3171.14444039) 3232.54444039 1.5699405035 -0.00227375564722)
  ((146.733513501 -3171.14444039) 3232.54444039 1.5651145533 -0.000139211525594)
  ((146.733513501 -3171.14444039) 3232.54444039 1.56223748877 -0.00389807591498)
  ((145.803556161 -3433.32511601) 3491.92511601 1.60883711725 -0.0410323951039)
  ((145.803556161 -3433.32511601) 3491.92511601 1.56286467496 -0.00386625281333)
  ((144.846447052 -3741.48827356) 3797.28827356 1.60552451793 -0.0378102777797)
  ((144.846447052 -3741.48827356) 3797.28827356 1.56360598826 -0.00391085150244)
  ((143.862753536 -4108.61501931) 4161.61501931 1.60224669611 -0.0347873604064)
  ((143.862753536 -4108.61501931) 4161.61501931 1.56446767262 -0.00403703769338)
  ((142.853058736 -4553.07760109) 4603.27760109 1.59900889568 -0.0322959623098)
  ((142.853058736 -4553.07760109) 4603.27760109 1.56576794467 -0.00456209271638)
  ((141.817961184 -5101.76068285) 5149.16068285 1.59581621062 -0.0337946378845)
  ((140.758074474 -5795.63507665) 5840.23507665 1.59267357394 -0.0297951490988)
  ((139.674026892 -6700.37078873) 6742.17078873 1.5895857471 -0.0258088749095)
  ((138.56646105 -7928.24793201) 7967.24793201 1.58655730987 -0.0218401006952)
  ((137.436033497 -9688.42322995) 9724.62322995 1.58359265079 -0.0178930953437)
  ((136.283414338 -12420.1372825) 12453.5372825 1.58069595814 -0.0139721068762)
  ((135.109286829 -17229.0882658) 17259.6882658 1.57787121156 -0.0100813580277)
  ((133.914346979 -27923.8852857) 27951.6852857 1.57512217416 -0.00622504179072)
  ((132.699303133 -72254.664488) 72279.664488 1.57245238537 -0.00240731692729)
  ((131.464875554 127243.417428) 127221.217428 -1.57172749924 0.00136769653995)
  ((130.211795995 34164.4009489) 34145.0009489 -1.57422909947 0.00509592184939)
  ((128.940807265 19849.5189516) 19832.9189516 -1.57664223722 0.00877333002401)
))
(princ)
