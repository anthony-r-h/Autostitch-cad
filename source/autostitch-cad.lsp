;;; AutoStitch native DWG adapter. Geometry is millimetres in WCS XY.
;;; User errors describe the failed operation; schema, ownership and attachment checks stay below.
(vl-load-com)
(setq ast:*cad-key* "AUTOSTITCH_V1")

(defun ast:cad-default-settings ()
  (list '(pitch . 3.0) '(slit-length . 1.5) (cons 'lean (* pi (/ 40.0 180.0)))
        '(handedness . 1) '(stitch-hand . 1) '(diameter . 0.5) '(corrections . T) '(reverse . nil)))

(defun ast:cad-get (key data) (cdr (assoc key data)))
(defun ast:cad-put (key value data)
  (if (assoc key data) (subst (cons key value) (assoc key data) data)
    (cons (cons key value) data)))
(defun ast:cad-require (value message)
  (if (not value) (progn (setq ast:*cad-error* message) (exit))) value)
(defun ast:cad-error-message (result fallback)
  (setq ast:*cad-last-error* (vl-catch-all-error-message result))
  (if ast:*cad-error* ast:*cad-error* fallback))
(defun ast:cad-unit-factor (/ units)
  (setq units (getvar "INSUNITS"))
  (cond ((= units 4) 1.0) ((= units 1) 25.4) ((= units 2) 304.8)
        ((= units 5) 10.0) ((= units 6) 1000.0)
        ((and (= units 0) (boundp 'ast:*unit-factor*)
              (numberp ast:*unit-factor*) (> ast:*unit-factor* 0)) ast:*unit-factor*)
        (T nil)))
(defun ast:cad-xy (point factor) (list (* factor (car point)) (* factor (cadr point))))
(defun ast:cad-z (point) (if (caddr point) (caddr point) 0.0))
(defun ast:cad-normal-p (data)
  (or (not (assoc 210 data)) (equal (cdr (assoc 210 data)) '(0.0 0.0 1.0) 1e-9)))

(defun ast:cad-pack (value / index)
  ;; Preserve full IEEE doubles in native Xrecord fields, never printed decimals.
  (cond ((eq (type value) 'REAL)
         (setq index (length ast:*cad-real-values*)
               ast:*cad-real-values* (append ast:*cad-real-values* (list (cons 40 value))))
         (cons 'ast-real index))
        ((and value (listp value)) (cons (ast:cad-pack (car value)) (ast:cad-pack (cdr value))))
        (T value)))
(defun ast:cad-unpack (value numbers)
  (cond ((and (listp value) (eq (car value) 'ast-real)) (nth (cdr value) numbers))
        ((and value (listp value)) (cons (ast:cad-unpack (car value) numbers) (ast:cad-unpack (cdr value) numbers)))
        (T value)))
(defun ast:cad-index-put (index value values / answer current item)
  (setq current 0)
  (foreach item values
    (setq answer (append answer (list (if (= current index) value item))) current (1+ current))) answer)

(defun ast:cad-record (entity / data dictionary record chunks numbers members primary member-index item retained pending)
  (if (and entity (setq data (entget entity)) (setq dictionary (cdr (assoc 360 data)))
           (setq record (dictsearch dictionary ast:*cad-key*)))
    (progn
      (setq chunks "" numbers nil members nil primary nil)
      (foreach item record
        (cond ((= (car item) 1) (setq chunks (strcat chunks (cdr item))))
              ((= (car item) 40) (setq numbers (append numbers (list (cdr item)))))
              ((= (car item) 90)
               (setq member-index (cdr item))
               (while (<= (length members) member-index) (setq members (append members (list nil)))))
              ((= (car item) 332)
               (setq members (if (numberp member-index) (ast:cad-index-put member-index (cdr item) members)
                               (append members (list (cdr item)))) member-index nil))
              ((= (car item) 333) (setq primary (cdr item)))
              ((= (car item) 334) (setq retained (append retained (list (cdr item)))))
              ((= (car item) 335) (setq pending (append pending (list (cdr item)))))))
      (setq data (vl-catch-all-apply 'read (list chunks)))
      (if (or (vl-catch-all-error-p data) (not (listp data)))
        (list '(schema . -1))
        (append (ast:cad-unpack data numbers) (list (cons 'link (cdr (assoc 331 record))))
                (if members (list (cons 'members members))) (if primary (list (cons 'primary primary)))
                (if retained (list (cons 'retained-outputs retained)))
                (if pending (list (cons 'pending-members pending))))))))

(defun ast:cad-write-record (entity data link / object dictionary old text-value chunks record references member index ast:*cad-real-values*)
  (setq references (if link (list (cons 331 link))) index 0)
  ;; Slot numbers survive erased soft references on save/reopen and preserve incidence indexes.
  (foreach member (ast:cad-get 'members data)
    (setq references (append references (list (cons 90 index)) (if member (list (cons 332 member)))) index (1+ index)))
  (if (ast:cad-get 'primary data) (setq references (append references (list (cons 333 (ast:cad-get 'primary data))))))
  (foreach member (ast:cad-get 'retained-outputs data)
    (if member (setq references (append references (list (cons 334 member))))))
  (foreach member (ast:cad-get 'pending-members data)
    (if member (setq references (append references (list (cons 335 member))))))
  (setq object (vlax-ename->vla-object entity)
        dictionary (vlax-vla-object->ename (vla-GetExtensionDictionary object))
        old (dictsearch dictionary ast:*cad-key*)
        ast:*cad-real-values* nil text-value (vl-prin1-to-string (ast:cad-pack
          (vl-remove-if '(lambda (item) (member (car item) '(members primary retained-outputs pending-members))) data))) chunks nil)
  (while (> (strlen text-value) 0)
    (setq chunks (append chunks (list (cons 1 (substr text-value 1 240))))
          text-value (substr text-value 241)))
  (if old
    (progn
      (setq record (entget (cdr (assoc -1 old))))
      (setq record (vl-remove-if '(lambda (item) (member (car item) '(1 40 90 331 332 333 334 335))) record))
      (ast:cad-require (entmod (append record chunks ast:*cad-real-values* references))
                       "BricsCAD could not save the stitching settings."))
    (progn
      (setq record (entmakex (append '((0 . "XRECORD") (100 . "AcDbXrecord") (280 . 1))
                                    chunks ast:*cad-real-values* references)))
      (ast:cad-require record "BricsCAD could not save the stitching settings.")
      (ast:cad-require (dictadd dictionary ast:*cad-key* record) "BricsCAD could not attach the stitching settings to this line.")))
  (ast:cad-require (and (equal (vl-remove-if '(lambda (item) (member (car item) '(members primary retained-outputs pending-members))) data)
                   (vl-remove-if '(lambda (item) (member (car item) '(link members primary retained-outputs pending-members))) (ast:cad-record entity)))
                   (equal (ast:cad-get 'members data) (ast:cad-get 'members (ast:cad-record entity)))
                   (equal (ast:cad-get 'primary data) (ast:cad-get 'primary (ast:cad-record entity)))
                   (equal (ast:cad-get 'retained-outputs data) (ast:cad-get 'retained-outputs (ast:cad-record entity)))
                   (equal (ast:cad-get 'pending-members data) (ast:cad-get 'pending-members (ast:cad-record entity))))
                   "The saved stitching settings could not be read back correctly.")
  T)

(defun ast:cad-extract (entity factor / data kind first-point last-point center radius start-angle sweep points bulges point bulge items item primitives index next-index count chord middle offset angle-value)
  (setq data (entget entity) kind (cdr (assoc 0 data)))
  (ast:cad-require (ast:cad-normal-p data) "This guide is tilted or has a reversed drawing plane. Redraw it in the standard XY plane.")
  (cond
    ((= kind "LINE")
     (setq first-point (cdr (assoc 10 data)) last-point (cdr (assoc 11 data)))
     (ast:cad-require (and (equal (ast:cad-z first-point) 0.0 1e-8)
                           (equal (ast:cad-z last-point) 0.0 1e-8)) "The stitch line must be flat at elevation 0. Move or redraw it in the XY plane.")
     (list (cons 'primitives (list (list '(kind . line) (cons 'a (ast:cad-xy first-point factor))
                                                   (cons 'b (ast:cad-xy last-point factor))))) '(closed . nil)))
    ((member kind '("ARC" "CIRCLE"))
     (setq center (cdr (assoc 10 data)) radius (* factor (cdr (assoc 40 data))))
     (ast:cad-require (equal (ast:cad-z center) 0.0 1e-8) "The stitch line must be flat at elevation 0. Move or redraw it in the XY plane.")
     (setq start-angle (if (= kind "CIRCLE") 0.0 (cdr (assoc 50 data)))
           sweep (if (= kind "CIRCLE") (* 2 pi) (- (cdr (assoc 51 data)) start-angle)))
     (if (<= sweep 0) (setq sweep (+ sweep (* 2 pi))))
     (list (cons 'primitives (list (list '(kind . arc) (cons 'center (ast:cad-xy center factor))
                 (cons 'radius radius) (cons 'start-angle start-angle) (cons 'sweep sweep))))
           (cons 'closed (= kind "CIRCLE"))))
    ((= kind "LWPOLYLINE")
     (ast:cad-require (or (not (assoc 38 data)) (equal (cdr (assoc 38 data)) 0.0 1e-8)) "The stitch line must be flat at elevation 0. Move or redraw it in the XY plane.")
     (setq points nil bulges nil point nil bulge 0.0)
     (foreach item data
       (cond ((= (car item) 10)
              (if point (setq points (append points (list point)) bulges (append bulges (list bulge))))
              (setq point (ast:cad-xy (cdr item) factor) bulge 0.0))
             ((= (car item) 42) (setq bulge (cdr item)))))
     (if point (setq points (append points (list point)) bulges (append bulges (list bulge))))
     (setq count (length points) index 0 primitives nil)
     (repeat (if (= 1 (logand 1 (cdr (assoc 70 data)))) count (1- count))
       (setq next-index (rem (1+ index) count) first-point (nth index points)
             last-point (nth next-index points) bulge (nth index bulges))
       (if (equal bulge 0.0 1e-12)
         (setq items (list '(kind . line) (cons 'a first-point) (cons 'b last-point)))
         (progn
           (setq chord (distance first-point last-point) angle-value (angle first-point last-point)
                 middle (mapcar '(lambda (x y) (/ (+ x y) 2.0)) first-point last-point)
                 offset (/ (* chord (- 1.0 (* bulge bulge))) (* 4.0 bulge))
                 center (list (- (car middle) (* offset (sin angle-value)))
                              (+ (cadr middle) (* offset (cos angle-value))))
                 radius (distance center first-point) sweep (* 4.0 (atan bulge))
                 items (list '(kind . arc) (cons 'center center) (cons 'radius radius)
                             (cons 'start-angle (angle center first-point)) (cons 'sweep sweep)))))
       (setq primitives (append primitives (list items)) index (1+ index)))
     (list (cons 'primitives primitives) (cons 'closed (= 1 (logand 1 (cdr (assoc 70 data)))))))
    (T (ast:cad-require nil "Select a line, arc, circle or 2D polyline to use as the stitch guide."))))

(defun ast:cad-output-original-p (guide output / record primary)
  (and output (entget output) (setq record (ast:cad-record output))
       (or (equal guide (ast:cad-get 'link record))
           (and (ast:cad-get 'topology-pending (ast:cad-record guide))
                (or (member guide (ast:cad-get 'members record))
                    (member guide (ast:cad-get 'pending-members record))))
           (and (equal (setq primary (ast:cad-get 'primary (ast:cad-record guide))) (ast:cad-get 'link record))
                (member guide (if (and primary (entget primary))
                  (ast:cad-get 'members (ast:cad-record primary)) (ast:cad-get 'members record)))))))

(defun ast:cad-backup-connections (connections / node incidence answer incidences)
  ;; Source snapshots remain on their canonical source; the output backs up topology only.
  (foreach node connections
    (setq incidences nil)
    (foreach incidence (ast:cad-get 'incidences node)
      (setq incidences (append incidences (list (vl-remove-if
        '(lambda (item) (eq (car item) 'source-route)) incidence)))))
    (setq answer (append answer (list (ast:cad-put 'incidences incidences node))))) answer)

(defun ast:cad-restore-connections (connections members / node incidence answer incidences source)
  (foreach node connections
    (setq incidences nil)
    (foreach incidence (ast:cad-get 'incidences node)
      (setq source (nth (ast:cad-get 'path incidence) members)
            incidences (append incidences (list (ast:cad-put 'source-route
              (ast:cad-get 'generated-route (ast:cad-record source)) incidence)))))
    (setq answer (append answer (list (ast:cad-put 'incidences incidences node))))) answer)

(defun ast:cad-group-info (guide / record primary primary-record output output-record members member saved valid copied backed missing connections pending)
  (setq record (ast:cad-record guide) primary (ast:cad-get 'primary record)
        primary-record (if (and primary (entget primary)) (ast:cad-record primary))
        output (ast:cad-get 'link record) output-record (if (and output (entget output)) (ast:cad-record output))
        pending (ast:cad-get 'topology-pending record)
        members (cond (primary-record (ast:cad-get 'members primary-record))
                      (pending (ast:cad-get 'members record))
                      (T (ast:cad-get 'members output-record)))
        backed (or (and pending members)
                   (and members (equal members (ast:cad-get 'members output-record))
                        (equal primary (ast:cad-get 'link output-record)))))
  ;; A copied source not present in the reciprocal membership starts independently.
  (if (not (member guide members)) (list (cons 'primary guide) (cons 'members (list guide)))
    (progn
      (setq valid T copied (or (and primary-record
        (not (equal (ast:cad-get 'identity primary-record) (cdr (assoc 5 (entget primary))))))
        (and (ast:cad-get 'output-identity output-record)
             (not (equal (ast:cad-get 'output-identity output-record) (cdr (assoc 5 (entget output))))))))
      (foreach member members
        (if (and member (entget member))
          (progn
            (setq saved (ast:cad-record member))
            (if (not (and (equal primary (ast:cad-get 'primary saved))
                          (if pending (ast:cad-get 'topology-pending saved)
                            (equal output (ast:cad-get 'link saved))))) (setq valid nil)))
          (setq missing T)))
      (cond
        ((and copied (or (not valid) (and missing (not backed))))
         (list (cons 'primary guide) (cons 'members (list guide))))
        (T
         (ast:cad-require valid "The saved connections are inconsistent. Copy the guide lines without their stitches, then connect the copies.")
         (ast:cad-require (or primary-record backed) "The saved connections cannot be read. Recreate this set from copies of its guide lines.")
         (setq connections (cond (primary-record (ast:cad-get 'connections primary-record))
           (pending (ast:cad-get 'connections record))
           (T (ast:cad-restore-connections (ast:cad-get 'connections output-record) members))))
         (list (cons 'primary primary) (cons 'members members) (cons 'missing-members missing)
               (cons 'connections connections)))))))

(defun ast:cad-canonical-value (value / decimal)
  (cond ((eq (type value) 'REAL)
         (setq decimal (rtos value 2 16))
         (if (vl-string-search "." decimal)
           (setq decimal (vl-string-right-trim "." (vl-string-right-trim "0" decimal))))
         (cond ((member decimal '("" "-0")) "0")
               ((= (substr decimal 1 1) ".") (strcat "0" decimal))
               ((= (substr decimal 1 2) "-.") (strcat "-0" (substr decimal 2)))
               (T decimal)))
        ((and value (listp value)) (cons (ast:cad-canonical-value (car value)) (ast:cad-canonical-value (cdr value))))
        (T value)))
(defun ast:cad-id-number (value / number tail split suffix valid)
  (if (and (= (type value) 'STR) (= (substr value 1 3) "ST-"))
    (progn
      (setq tail (substr value 4) split (vl-string-search "-" tail)
            number (atoi tail) suffix (if split (substr tail (+ split 2)))
            valid (and (> number 0) (= (if split (substr tail 1 split) tail) (itoa number))))
      (if split
        (setq valid (and valid (> (strlen suffix) 0)
          (/= (substr suffix 1 1) "-") (/= (substr suffix (strlen suffix)) "-")
          (not (vl-string-search "--" suffix))
          (vl-every '(lambda (code) (or (= code 45) (and (>= code 65) (<= code 90)))) (vl-string->list suffix)))))
      (if valid number))))

(defun ast:cad-next-stitch-id (/ counter number block selection index record value)
  ;; The drawing counter participates in the same Undo transaction as its owner.
  (setq counter (dictsearch (namedobjdict) "AUTOSTITCH_IDS_V1")
        number (if counter (cdr (assoc 90 counter)) 0))
  (while (setq block (tblnext "BLOCK" (not block)))
    (if (setq value (ast:cad-id-number (cdr (assoc 2 block)))) (setq number (max number value))))
  (if (setq selection (ssget "_X" '((0 . "LINE,ARC,CIRCLE,LWPOLYLINE,INSERT"))))
    (progn
      (setq index 0)
      (repeat (sslength selection)
        (setq record (ast:cad-record (ssname selection index)) index (1+ index))
        (if (setq value (ast:cad-id-number (ast:cad-get 'stitch-id record))) (setq number (max number value))))))
  (setq number (1+ number))
  (if counter
    (ast:cad-require (entmod (subst (cons 90 number) (assoc 90 counter) (entget (cdr (assoc -1 counter)))))
      "Could not reserve a stitch ID.")
    (ast:cad-require (dictadd (namedobjdict) "AUTOSTITCH_IDS_V1"
      (entmakex (list '(0 . "XRECORD") '(100 . "AcDbXrecord") '(280 . 1) (cons 90 number))))
      "Could not reserve a stitch ID."))
  (strcat "ST-" (itoa number)))

(defun ast:cad-assigned-id (guide output / record saved identity)
  (setq record (ast:cad-record guide) saved (if output (ast:cad-record output))
        identity (ast:cad-get 'stitch-id record))
  (cond
    ((and (ast:cad-id-number identity)
          (equal (ast:cad-get 'stitch-owner record) (cdr (assoc 5 (entget guide))))
          (or (not (tblsearch "BLOCK" identity))
              (and output (= identity (cdr (assoc 2 (entget output))))))) identity)
    ((and output (equal (ast:cad-get 'output-identity saved) (cdr (assoc 5 (entget output))))
          (ast:cad-id-number (ast:cad-get 'stitch-id saved))
          (or (not (tblsearch "BLOCK" (ast:cad-get 'stitch-id saved)))
              (= (ast:cad-get 'stitch-id saved) (cdr (assoc 2 (entget output)))))) (ast:cad-get 'stitch-id saved))
    (T (ast:cad-next-stitch-id))))

(defun ast:cad-ensure-stitch-id (guide / owner record output identity retained)
  (setq owner (ast:cad-stitch-owner guide) record (ast:cad-record owner)
        output (ast:cad-get 'link record))
  (if (not (ast:cad-output-original-p owner output)) (setq output nil))
  (if (ast:cad-get 'topology-pending record)
    (progn
      (setq retained (vl-some '(lambda (candidate)
      (if (and (ast:cad-pending-output-p candidate (ast:cad-get 'members (ast:cad-group-info owner)))
               (equal (cdr (assoc 2 (entget candidate))) (ast:cad-get 'stitch-id record))) candidate))
      (ast:cad-get 'retained-outputs record)))
      (if retained (setq output retained))))
  (setq identity (ast:cad-assigned-id owner output))
  (if (not (and (equal identity (ast:cad-get 'stitch-id record))
                (equal (ast:cad-get 'stitch-owner record) (cdr (assoc 5 (entget owner))))))
    (progn
      (if (not record) (setq record (list '(schema . 1) '(rule . 1)
        (cons 'identity (cdr (assoc 5 (entget owner)))))))
      (setq record (ast:cad-put 'stitch-id identity
        (ast:cad-put 'stitch-owner (cdr (assoc 5 (entget owner))) record)))
      (ast:cad-write-record owner (vl-remove-if '(lambda (item) (eq (car item) 'link)) record) output)))
  identity)

(defun ast:cad-stitch-id (guide / owner record)
  (setq owner (ast:cad-stitch-owner guide) record (ast:cad-record owner))
  (if (and (ast:cad-id-number (ast:cad-get 'stitch-id record))
           (equal (ast:cad-get 'stitch-owner record) (cdr (assoc 5 (entget owner)))))
    (ast:cad-get 'stitch-id record) ""))

(defun ast:cad-stitch-owner (guide / group primary)
  (setq group (ast:cad-group-info guide) primary (ast:cad-get 'primary group))
  (if (and primary (entget primary)) primary
    (vl-some '(lambda (member) (if (and member (entget member)) member))
      (ast:cad-get 'members group))))

(defun ast:cad-output-signature (output / entity data count hash-one hash-two canonical index code)
  ;; Fingerprint actual cut content without duplicating the opening recipe in metadata.
  (setq entity (tblobjname "BLOCK" (cdr (assoc 2 (entget output)))) count 0 hash-one 5381.0 hash-two 17.0)
  (while (and entity (setq entity (entnext entity))
              (/= "ENDBLK" (cdr (assoc 0 (setq data (entget entity))))))
    (setq count (1+ count)
          canonical (vl-prin1-to-string (ast:cad-canonical-value
                     (vl-remove-if-not '(lambda (item) (member (car item) '(0 1 7 8 10 11 40 41 42 43 50 62 70 72 73 90 210 370 420))) data)))
          index 1)
    (while (<= index (strlen canonical))
      (setq code (ascii (substr canonical index 1))
            hash-one (rem (+ (* hash-one 131.0) code) 2147483629.0)
            hash-two (rem (+ (* hash-two 137.0) code) 2147483587.0)
            index (1+ index))))
  (list count (fix hash-one) (fix hash-two)
        (cdr (assoc 10 (tblsearch "BLOCK" (cdr (assoc 2 (entget output))))))))
(defun ast:cad-placement-ok-p (output / data)
  (setq data (entget output))
  (and (= (cdr (assoc 0 data)) "INSERT")
       (equal (cdr (assoc 10 data)) '(0.0 0.0 0.0) 1e-8)
       (equal (cdr (assoc 41 data)) 1.0 1e-9)
       (equal (cdr (assoc 42 data)) 1.0 1e-9)
       (equal (cdr (assoc 43 data)) 1.0 1e-9)
       (equal (cdr (assoc 50 data)) 0.0 1e-9)
       (ast:cad-normal-p data)))

(defun ast:cad-transform-point (point insertion rotation factor / cosine sine)
  (setq cosine (cos rotation) sine (sin rotation))
  (list (+ (* factor (car insertion)) (- (* cosine (car point)) (* sine (cadr point))))
        (+ (* factor (cadr insertion)) (* sine (car point)) (* cosine (cadr point)))))
(defun ast:cad-common-placement-p (output original current factor / data insertion rotation primitive transformed item)
  (if (and output original (setq data (entget output))
           (equal (cdr (assoc 41 data)) 1.0 1e-9)
           (equal (cdr (assoc 42 data)) 1.0 1e-9)
           (equal (cdr (assoc 43 data)) 1.0 1e-9)
           (equal (ast:cad-z (cdr (assoc 10 data))) 0.0 1e-8)
           (ast:cad-normal-p data))
    (progn
      (setq insertion (cdr (assoc 10 data)) rotation (cdr (assoc 50 data)) transformed nil)
      (foreach primitive (ast:cad-get 'primitives original)
        (if (eq (ast:cad-get 'kind primitive) 'line)
          (setq item (list '(kind . line)
              (cons 'a (ast:cad-transform-point (ast:cad-get 'a primitive) insertion rotation factor))
              (cons 'b (ast:cad-transform-point (ast:cad-get 'b primitive) insertion rotation factor))))
          (setq item (list '(kind . arc)
              (cons 'center (ast:cad-transform-point (ast:cad-get 'center primitive) insertion rotation factor))
              (cons 'radius (ast:cad-get 'radius primitive))
              (cons 'start-angle (rem (+ (ast:cad-get 'start-angle primitive) rotation (* 2 pi)) (* 2 pi)))
              (cons 'sweep (ast:cad-get 'sweep primitive)))))
        (setq transformed (append transformed (list item))))
      (equal (list (cons 'primitives transformed) (cons 'closed (ast:cad-get 'closed original))) current 1e-7))))

(defun ast:cad-read-base (entity / data guide record output factor route settings landmarks stale common state ranges members primary group)
  (ast:cad-require (and entity (setq data (entget entity))) "The selected line was deleted. Select another stitch line.")
  (setq guide entity record (ast:cad-record entity))
  (if (= (cdr (assoc 0 data)) "INSERT")
    (progn
      (setq guide (ast:cad-get 'link record))
      (if (not (and guide (entget guide)))
        (setq guide (vl-some '(lambda (member)
          (if (and member (entget member)
                   (or (and (equal entity (ast:cad-get 'link (ast:cad-record member)))
                            (equal (ast:cad-get 'link record) (ast:cad-get 'primary (ast:cad-record member))))
                       (and (member member (ast:cad-get 'pending-members record))
                            (member entity (ast:cad-get 'retained-outputs (ast:cad-record member)))))) member))
          (append (ast:cad-get 'pending-members record) (ast:cad-get 'members record)))))
      (ast:cad-require (and guide (entget guide)
                           (or (equal entity (ast:cad-get 'link (ast:cad-record guide)))
                               (and (member guide (ast:cad-get 'pending-members record))
                                    (member entity (ast:cad-get 'retained-outputs (ast:cad-record guide))))))
                       "These stitches have no editable guide link. Select the original guide line instead.")
      (setq record (ast:cad-record guide))))
  (ast:cad-require (or (null record) (member (list (ast:cad-get 'schema record) (ast:cad-get 'rule record))
                                            '((1 1) (2 2)))) "This version of Autostitch cannot read the saved settings for this line. Use the version that created them.")
  (setq group (ast:cad-group-info guide) members (ast:cad-get 'members group) primary (ast:cad-get 'primary group))
  (if (and (ast:cad-get 'primary record) (= 1 (length members)))
    (setq record (vl-remove-if '(lambda (item) (member (car item) '(primary members connections link))) record)))
  (setq factor (if (ast:cad-get 'factor record)
                 (ast:cad-get 'factor record) (ast:cad-unit-factor)))
  (ast:cad-require factor "Set the drawing units to millimetres or inches, then select the line again.")
  (setq route (ast:cad-extract guide factor) output (ast:cad-get 'link record))
  (if (not (ast:cad-output-original-p guide output)) (setq output nil))
  (if output
    (ast:cad-require (member (list (ast:cad-get 'schema (ast:cad-record output))
                                  (ast:cad-get 'rule (ast:cad-record output))) '((1 1) (2 2)))
                     "This version of Autostitch cannot read these saved stitches. Use the version that created them."))
  (setq common (ast:cad-common-placement-p output (ast:cad-get 'generated-route record) route factor))
  (setq settings (if (ast:cad-get 'settings record) (ast:cad-get 'settings record) (ast:cad-default-settings))
        landmarks (ast:cad-get 'landmarks record)
        stale (or (ast:cad-get 'topology-pending record) (null output)
                  (and (not common) (not (equal route (ast:cad-get 'generated-route record) 1e-8)))
                  (and output (not (equal 8 (ast:cad-get 'display-version (ast:cad-record output)))))
                  (and output (= 2 (ast:cad-get 'schema record))
                       (not (equal 1 (ast:cad-get 'junction-version (ast:cad-record output)))))
                  (not (equal settings (ast:cad-get 'generated-settings record)))
                  (not (equal landmarks (ast:cad-get 'generated-landmarks record)))
                  (and output (not (equal (ast:cad-output-signature output)
                                          (ast:cad-get 'signature (ast:cad-record output)))))
                  (and (not common) (not (ast:cad-placement-ok-p output)))))
  (setq state (list '(ok . T) (cons 'guide guide) (cons 'output output) (cons 'route route)
        (cons 'factor factor) (cons 'settings settings) (cons 'landmarks landmarks)
        (cons 'record record) (cons 'stale stale) (cons 'common-placement common)
        (cons 'primary primary) (cons 'members members)
        (cons 'connections (ast:cad-get 'connections group))
        (cons 'missing-members (ast:cad-get 'missing-members group))
        (cons 'connection-conflict (if (ast:cad-get 'missing-members group)
          "A connected stitch line was deleted. Remove missing lines to repair the generated stitches."))
        (cons 'placement-conflict (and output (not common) (not (ast:cad-placement-ok-p output))))))
  (setq ranges (ast:cad-resolve-ranges state settings))
  (setq state (ast:cad-put 'settings (ast:cad-get 'settings ranges) state))
  (if (ast:cad-get 'error ranges)
    (setq state (ast:cad-put 'range-conflict (ast:cad-get 'error ranges) (ast:cad-put 'stale T state))))
  state)
(defun ast:cad-read-inner (entity / state member other common stale conflict)
  (setq state (ast:cad-read-base entity) common T stale (ast:cad-get 'stale state)
        conflict (ast:cad-get 'placement-conflict state))
  (foreach member (ast:cad-get 'members state)
    (if (and member (entget member))
      (progn
        (setq other (if (equal member (ast:cad-get 'guide state)) state (ast:cad-read-base member)))
        (if (ast:cad-get 'stale other) (setq stale T))
        (if (not (ast:cad-get 'common-placement other)) (setq common nil))
        (if (ast:cad-get 'placement-conflict other) (setq conflict T)))
      (setq stale T common nil)))
  (setq state (ast:cad-put 'placement-conflict conflict
    (ast:cad-put 'common-placement common (ast:cad-put 'stale stale state))))
  (if (member 'ast:match-decorate (atoms-family 0)) (ast:match-decorate state) state))
(defun ast:cad-read (entity / ast:*cad-error* result)
  (setq result (vl-catch-all-apply 'ast:cad-read-inner (list entity)))
  (if (vl-catch-all-error-p result)
    (list '(ok . nil) (cons 'error (ast:cad-error-message result
      "Could not read this stitch line. Select its original guide, or reload Autostitch and try again."))) result))

(defun ast:cad-project (entity world-point / closest parameter index start-parameter station factor data kind record)
  (setq data (entget entity) kind (cdr (assoc 0 data)) record (ast:cad-record entity)
        factor (if (ast:cad-get 'factor record)
                 (ast:cad-get 'factor record) (ast:cad-unit-factor))
        closest (vlax-curve-getClosestPointTo entity world-point)
        parameter (vlax-curve-getParamAtPoint entity closest)
        index (if (= kind "LWPOLYLINE") (fix parameter) 0)
        start-parameter (if (= kind "LWPOLYLINE") index (vlax-curve-getStartParam entity)))
  (if (and (= kind "LWPOLYLINE") (= parameter (vlax-curve-getEndParam entity)))
    (setq index (1- index) start-parameter index))
  (setq station (* factor (- (vlax-curve-getDistAtParam entity parameter)
                             (vlax-curve-getDistAtParam entity start-parameter))))
  (list (cons 'primitive index) (cons 'station station)))

(defun ast:cad-range-anchor (entity attachment)
  (append attachment (list (cons 'source-route (ast:cad-get 'route (ast:cad-read entity))))))
(defun ast:cad-rebase-ranges (settings route / pair anchor)
  (foreach pair '((start . start-anchor) (end . end-anchor) (phase . phase-anchor))
    (if (setq anchor (ast:cad-get (cdr pair) settings))
      (setq settings (ast:cad-put (cdr pair) (ast:cad-put 'source-route route anchor) settings))))
  settings)
(defun ast:cad-resolve-ranges (state settings / pair anchor snapshot fake-state primitives index station total cursor error)
  (setq primitives (ast:cad-get 'primitives (ast:cad-get 'route state)))
  (foreach pair '((start . start-anchor) (end . end-anchor) (phase . phase-anchor))
    (if (setq anchor (ast:cad-get (cdr pair) settings))
      (progn
        (setq snapshot (ast:cad-get 'source-route anchor))
        (if (null snapshot) (setq snapshot (ast:cad-get 'attachment-route (ast:cad-get 'record state))))
        (setq fake-state (ast:cad-put 'record (ast:cad-put 'attachment-route snapshot (ast:cad-get 'record state)) state))
        (cond
          ((or (null snapshot) (not (ast:cad-attachments-valid-p fake-state (list anchor))))
           (setq error "The line changed, so its saved start or end cannot be located. Pick it again with Set start or Set end."))
          (T
           (setq index (ast:cad-get 'primitive anchor) station (ast:cad-get 'station anchor))
           (if (or (not (numberp index)) (< index 0) (>= index (length primitives))
                   (not (numberp station)) (< station 0.0) (> station (+ 1e-8 (ast:g-length (nth index primitives)))))
             (setq error "The saved start or end is beyond the edited line. Pick a new point with Set start or Set end.")
             (progn
               (setq total station cursor 0)
               (while (< cursor index) (setq total (+ total (ast:g-length (nth cursor primitives))) cursor (1+ cursor)))
               (setq settings (ast:cad-put (car pair) total settings)))))))
      (if (and (assoc (car pair) settings)
               (not (and (eq (car pair) 'phase) (equal (ast:cad-get 'phase settings) 0.0 1e-8)))
               (ast:cad-get 'attachment-route (ast:cad-get 'record state))
               (not (ast:cad-attachments-valid-p state (list '((primitive . 0) (station . 0.0))))))
        (setq error "The line changed, so its saved start or end cannot be located. Pick it again with Set start or Set end."))))
  (list (cons 'settings settings) (cons 'error error)))

(defun ast:cad-inject (stage)
  (if (and (boundp 'ast:*cad-fail-stage*) (equal ast:*cad-fail-stage* stage))
    (ast:cad-require nil (strcat "Injected failure: " stage))))
(defun ast:cad-layer-unlocked-p (name / data)
  (setq data (tblsearch "LAYER" name))
  (or (null data) (= 0 (logand 4 (cdr (assoc 70 data))))))

(defun ast:cad-ensure-display-layer (name / data)
  (ast:cad-require (ast:cad-layer-unlocked-p name) "Unlock the stitch display layers before generating.")
  (if (not (tblsearch "LAYER" name))
    (ast:cad-require (entmake (list '(0 . "LAYER") '(100 . "AcDbSymbolTableRecord")
      '(100 . "AcDbLayerTableRecord") (cons 2 name) '(70 . 0) '(62 . 7) '(6 . "Continuous")
      '(290 . 1))) "Could not create stitch display layer."))
  (setq data (entget (tblobjname "LAYER" name)))
  (ast:cad-require (entmod (ast:cad-put 290 1
    (ast:cad-put 70 (logand -2 (cdr (assoc 70 data))) (ast:cad-put 62 7 data))))
    "Could not enable stitch display layer.")
  name)

;; Connected opening lists are unordered. Resolve each interval from its own arm.
(defun ast:cad-orient-opening (opening primitive settings / tangent radial lean axis)
  (if (= (ast:cad-get 'type opening) 'slit)
    (progn
      (setq tangent (if (= (ast:cad-get 'kind primitive) 'line) (ast:g-tangent primitive 0.0)
        (progn (setq radial (ast:g-sub (ast:cad-get 'center opening) (ast:cad-get 'center primitive)))
          (ast:g-mul (ast:g-left radial) (/ (ast:g-sign (ast:cad-get 'sweep primitive)) (ast:g-norm radial))))))
      (setq lean (ast:g-lean settings)
            axis (ast:g-add (ast:g-mul tangent (cos lean)) (ast:g-mul (ast:g-left tangent) (sin lean))))
      (if (< (ast:g-dot axis (ast:cad-get 'axis opening)) 0.0)
        (setq opening (ast:cad-put 'axis (ast:g-mul (ast:cad-get 'axis opening) -1.0) opening)))))
  opening)
(defun ast:cad-display-intervals (solution settings / records interval primitive first-opening last-opening point)
  (foreach interval (ast:cad-get 'intervals solution)
    (setq primitive (nth (ast:cad-get 'primitive interval) (ast:cad-get 'primitives solution)))
    (if (= (ast:cad-get 'kind interval) 'junction)
      (progn
        (setq point (ast:cad-get 'from interval)
              first-opening (vl-some '(lambda (item) (if (< (ast:g-dist point (ast:cad-get 'center item)) 1e-8) item)) (ast:cad-get 'openings solution))
              point (ast:cad-get 'to interval)
              last-opening (vl-some '(lambda (item) (if (< (ast:g-dist point (ast:cad-get 'center item)) 1e-8) item)) (ast:cad-get 'openings solution)))
        (ast:cad-require (and first-opening last-opening) "Autostitch could not connect the thread between the calculated holes.")
        (setq first-opening (ast:cad-orient-opening first-opening primitive settings)
              last-opening (ast:cad-orient-opening last-opening primitive settings)))
      (setq first-opening (ast:g-slit primitive (ast:cad-get 'start-station interval) settings)
            last-opening (ast:g-slit primitive (ast:cad-get 'end-station interval) settings)))
    (setq records (cons (append interval (list (cons 'guide primitive) (cons 'from-opening first-opening) (cons 'to-opening last-opening))) records)))
  (reverse records))
(defun ast:cad-display-point (point factor)
  (append (mapcar '(lambda (value) (/ value factor)) point) '(0.0)))
(defun ast:cad-display-line (first-point last-point layer factor)
  (ast:cad-require (entmake (list '(0 . "LINE") (cons 8 layer) '(62 . 7) '(370 . 9)
    (cons 10 (ast:cad-display-point first-point factor)) (cons 11 (ast:cad-display-point last-point factor)))) "Could not create stitch display line."))
(defun ast:cad-thread-tip (opening sign)
  (if (= (ast:cad-get 'type opening) 'round) (ast:cad-get 'center opening)
    (ast:g-add (ast:cad-get 'center opening) (ast:g-mul (ast:cad-get 'axis opening) (* sign 0.5 (ast:cad-get 'length opening))))))
(defun ast:cad-write-thread (interval factor)
  (ast:cad-display-line (ast:cad-thread-tip (ast:cad-get 'from-opening interval) 1.0)
    (ast:cad-thread-tip (ast:cad-get 'to-opening interval) -1.0) "AUTOSTITCH_STITCHES" factor))
(defun ast:cad-ensure-annotation-layer (/ layer)
  (if (not (tblsearch "LAYER" "AUTOSTITCH_UI"))
    (ast:cad-require (entmake '((0 . "LAYER") (100 . "AcDbSymbolTableRecord")
      (100 . "AcDbLayerTableRecord") (2 . "AUTOSTITCH_UI") (70 . 0)
      (62 . 7) (6 . "Continuous") (290 . 0))) "Could not create nonplotting marker layer."))
  (setq layer (entget (tblobjname "LAYER" "AUTOSTITCH_UI")))
  (ast:cad-require (= 0 (logand 4 (cdr (assoc 70 layer)))) "Unlock AUTOSTITCH_UI to show adjusted spacing.")
  (ast:cad-require (= 0 (cdr (assoc 290 layer))) "Set AUTOSTITCH_UI to nonplotting before showing adjusted spacing."))
(defun ast:cad-spacing-label (distance / label dot)
  (setq label (rtos distance 2 2))
  (if (= "." (substr label 1 1)) (setq label (strcat "0" label)))
  (if (not (vl-string-search "." label)) (setq label (strcat label ".")))
  (setq dot (vl-string-search "." label))
  (while (< (- (strlen label) dot) 3) (setq label (strcat label "0")))
  label)
(defun ast:cad-spacing-anchor (first-point last-point primitives / midpoint arc radial)
  (setq midpoint (ast:g-mul (ast:g-add first-point last-point) 0.5)
        arc (vl-some '(lambda (primitive)
          (if (and (= (ast:cad-get 'kind primitive) 'arc) (ast:g-point-on primitive last-point)
            (< (abs (- (ast:g-dist first-point (ast:cad-get 'center primitive)) (ast:cad-get 'radius primitive))) 1e-7))
            primitive)) primitives))
  (if arc
    (progn
      (setq radial (ast:g-sub midpoint (ast:cad-get 'center arc)))
      (setq midpoint (if (> (ast:g-norm radial) 1e-10)
        (ast:g-add (ast:cad-get 'center arc) (ast:g-mul radial (/ (ast:cad-get 'radius arc) (ast:g-norm radial))))
        (ast:g-point arc (* 0.5 (ast:g-length arc)))))))
  midpoint)
(defun ast:cad-write-spacing-label (first-point last-point primitives factor / rotation anchor)
  (setq rotation (angle first-point last-point))
  (if (and (> rotation (/ pi 2.0)) (<= rotation (* 1.5 pi))) (setq rotation (- rotation pi)))
  (setq anchor (ast:cad-display-point (ast:cad-spacing-anchor first-point last-point primitives) factor))
  (ast:cad-require (entmake (list '(0 . "TEXT") '(8 . "AUTOSTITCH_UI") '(62 . 7) '(370 . 9)
    (cons 10 anchor) (cons 11 anchor) (cons 40 (/ 0.30 factor))
    (cons 1 (ast:cad-spacing-label (ast:g-dist first-point last-point)))
    '(7 . "Standard") (cons 50 rotation) '(72 . 1) '(73 . 2)))
    "Could not show adjusted spacing."))
(defun ast:cad-write-spacing-marks (opening factor / normal half-width tip first-point last-point sign)
  (setq normal (ast:g-left (ast:cad-get 'axis opening))
        half-width (* 0.65 (min 0.45 (* 0.3 (ast:cad-get 'length opening)))))
  (foreach sign '(-1.0 1.0)
    (setq tip (ast:cad-thread-tip opening sign)
          first-point (ast:g-add tip (ast:g-mul normal half-width))
          last-point (ast:g-sub tip (ast:g-mul normal half-width)))
    (ast:cad-require (entmake (list '(0 . "LWPOLYLINE") '(100 . "AcDbEntity")
      '(8 . "AUTOSTITCH") '(62 . 7) '(370 . 30)
      '(100 . "AcDbPolyline") '(90 . 2) '(70 . 0) '(43 . 0.0)
      (cons 10 (mapcar '(lambda (value) (/ value factor)) first-point))
      (cons 10 (mapcar '(lambda (value) (/ value factor)) last-point))))
      "Could not create changed-spacing crossbar.")))

(defun ast:cad-write-virtual-slit (opening factor / ends first-point delta index)
  ;; Four real dash strokes keep construction legible independently of LTSCALE.
  (setq ends (ast:g-ends opening) first-point (car ends) delta (ast:g-sub (cadr ends) first-point))
  (foreach index '(0 2 4 6)
    (ast:cad-display-line (ast:g-add first-point (ast:g-mul delta (/ index 7.0)))
      (ast:g-add first-point (ast:g-mul delta (/ (1+ index) 7.0))) "AUTOSTITCH" factor)))
(defun ast:cad-write-hole-fill (opening factor / center radius)
  ;; A zero-inner-diameter CAD donut fills the exact circular opening.
  (setq center (mapcar '(lambda (value) (/ value factor)) (ast:cad-get 'center opening))
        radius (/ (ast:cad-get 'diameter opening) (* 4.0 factor)))
  (ast:cad-require (entmake (list '(0 . "LWPOLYLINE") '(100 . "AcDbEntity")
    '(8 . "AUTOSTITCH") '(62 . 7) '(370 . 0) '(100 . "AcDbPolyline")
    '(90 . 2) '(70 . 1) (cons 43 (* 2.0 radius))
    (cons 10 (list (- (car center) radius) (cadr center))) '(42 . 1.0)
    (cons 10 (list (+ (car center) radius) (cadr center))) '(42 . 1.0)))
    "Could not fill round stitch hole."))

(defun ast:cad-unique-name (identity revision / number name base)
  (setq number 1 base (strcat "AUTOSTITCH_" identity "_R" (itoa revision)) name base)
  (while (tblsearch "BLOCK" name)
    (setq number (1+ number) name (strcat base "_" (itoa number)))) name)

(defun ast:cad-publish-name (temporary identity output / blocks old archive number)
  ;; Move the old definition aside rather than redefining geometry shared by static copies.
  (setq blocks (vla-get-Blocks (vla-get-ActiveDocument (vlax-get-acad-object))))
  (if (tblsearch "BLOCK" identity)
    (progn
      (ast:cad-require (and output (= identity (cdr (assoc 2 (entget output)))))
        "This stitch ID is already used by another block. Select the guide again and retry.")
      (setq old (vla-Item blocks identity) number 1 archive (strcat "AST_OLD_" (vla-get-Handle old)))
      (while (tblsearch "BLOCK" archive)
        (setq number (1+ number) archive (strcat "AST_OLD_" (vla-get-Handle old) "_" (itoa number))))
      (vla-put-Name old archive)))
  (vla-put-Name (vla-Item blocks temporary) identity)
  (ast:cad-inject "block-name")
  identity)

(defun ast:cad-write-opening (opening factor / center axis half-size first-point last-point)
  (setq center (ast:cad-get 'center opening))
  (if (eq (ast:cad-get 'type opening) 'slit)
    (progn
      (setq axis (ast:cad-get 'axis opening) half-size (/ (ast:cad-get 'length opening) 2.0)
            first-point (mapcar '(lambda (coordinate direction) (/ (- coordinate (* half-size direction)) factor)) center axis)
            last-point (mapcar '(lambda (coordinate direction) (/ (+ coordinate (* half-size direction)) factor)) center axis))
      (ast:cad-require (entmake (list '(0 . "LINE") '(8 . "AUTOSTITCH") '(62 . 7) '(370 . 30)
                                     (cons 10 (append first-point '(0.0)))
                                     (cons 11 (append last-point '(0.0))))) "Could not create slit."))
    (ast:cad-require (entmake (list '(0 . "CIRCLE") '(8 . "AUTOSTITCH") '(62 . 7) '(370 . 0)
                     (cons 10 (append (mapcar '(lambda (value) (/ value factor)) center) '(0.0)))
                     (cons 40 (/ (ast:cad-get 'diameter opening) (* 2 factor))))) "Could not create hole.")))

(defun ast:cad-update-markers (state settings landmarks)
  (if (member 'ast:markers-update (atoms-family 0))
    (ast:markers-update (ast:cad-get 'guide state) settings landmarks
                       (ast:cad-get 'factor state) (ast:cad-get 'route state))))

(defun ast:cad-write-inner (state settings landmarks solution / guide output old-output name record revision identity stitch-id factor data opening owner object corrected-count interval display changed-points)
  (setq guide (ast:cad-get 'guide state) old-output (ast:cad-get 'output state)
        factor (ast:cad-get 'factor state) record (ast:cad-get 'record state)
        revision (1+ (if (numberp (ast:cad-get 'revision record)) (ast:cad-get 'revision record) 0))
        identity (cdr (assoc 5 (entget guide))) stitch-id (ast:cad-assigned-id guide old-output)
        name (ast:cad-unique-name identity revision))
  (setq settings (ast:cad-rebase-ranges settings (ast:cad-get 'route state)))
  (setq display (ast:cad-display-intervals solution settings))
  (foreach interval display
    (if (= (ast:cad-get 'kind interval) 'corrected)
      (setq changed-points (cons (ast:cad-get 'center (ast:cad-get 'from-opening interval))
                          (cons (ast:cad-get 'center (ast:cad-get 'to-opening interval)) changed-points)))))
  (foreach interval (ast:cad-get 'corner-adjustments solution)
    (setq changed-points (cons (ast:cad-get 'center interval) changed-points)))
  (ast:cad-ensure-display-layer "AUTOSTITCH")
  (ast:cad-ensure-display-layer "AUTOSTITCH_STITCHES")
  (if changed-points (ast:cad-ensure-annotation-layer))
  (setvar "LWDISPLAY" 1)
  (setvar "FILLMODE" 1)
  (ast:cad-require (entmake (list '(0 . "BLOCK") (cons 2 name) '(70 . 0) '(10 0.0 0.0 0.0) '(8 . "AUTOSTITCH"))) "Could not create block definition.")
  (setq ast:*cad-block-open* T)
  (ast:cad-inject "block-start")
  (foreach opening (ast:cad-get 'openings solution)
    (ast:cad-write-opening opening factor)
    (if (= (ast:cad-get 'type opening) 'round) (ast:cad-write-hole-fill opening factor))
    (if (and (= (ast:cad-get 'type opening) 'slit)
             (vl-some '(lambda (point) (< (ast:g-dist point (ast:cad-get 'center opening)) 1e-8)) changed-points))
      (ast:cad-write-spacing-marks opening factor)))
  (foreach interval display
    (ast:cad-write-thread interval factor)
    (if (= (ast:cad-get 'kind interval) 'corrected)
      (ast:cad-write-spacing-label (ast:cad-get 'center (ast:cad-get 'from-opening interval))
        (ast:cad-get 'center (ast:cad-get 'to-opening interval)) (list (ast:cad-get 'guide interval)) factor)))
  (foreach interval (ast:cad-get 'corner-adjustments solution)
    (ast:cad-write-spacing-label (ast:cad-get 'virtual-center interval) (ast:cad-get 'center interval) (ast:cad-get 'primitives solution) factor))
  (foreach opening (ast:cad-get 'virtual-slits solution) (ast:cad-write-virtual-slit opening factor))
  (ast:cad-inject "display")
  (ast:cad-require (entmake '((0 . "ENDBLK"))) "Could not complete block definition.")
  (setq ast:*cad-block-open* nil)
  (ast:cad-inject "geometry")
  (setq name (ast:cad-publish-name name stitch-id old-output))
  (if old-output
    (progn
      (setq data (entget old-output))
      (setq data (subst (cons 2 name) (assoc 2 data) data)
            data (ast:cad-put 8 "AUTOSTITCH" data)
            data (subst '(10 0.0 0.0 0.0) (assoc 10 data) data)
            data (subst '(50 . 0.0) (assoc 50 data) data)
            data (ast:cad-put 41 1.0 data)
            data (ast:cad-put 42 1.0 data)
            data (ast:cad-put 43 1.0 data)
            data (ast:cad-put 210 '(0.0 0.0 1.0) data))
      (ast:cad-require (entmod data) "Could not replace output block.")
      (setq output old-output) (entupd output))
    (progn
      (setq owner (vlax-ename->vla-object (cdr (assoc 330 (entget guide))))
            object (vla-InsertBlock owner (vlax-3d-point '(0.0 0.0 0.0)) name 1.0 1.0 1.0 0.0))
      (vla-put-Layer object "AUTOSTITCH")
      (setq output (vlax-vla-object->ename object))
      (ast:cad-require (equal (cdr (assoc 330 (entget guide))) (cdr (assoc 330 (entget output))))
                       "Output was not inserted in the guide's space.")))
  (setq record (list '(schema . 1) '(rule . 1) (cons 'identity identity) (cons 'revision revision)
          (cons 'stitch-id stitch-id) (cons 'stitch-owner identity)
          (cons 'settings settings) (cons 'landmarks landmarks) (cons 'attachment-route (ast:cad-get 'route state))
          (cons 'generated-route (ast:cad-get 'route state)) (cons 'generated-settings settings)
          (cons 'generated-landmarks landmarks) (cons 'factor factor)))
  (ast:cad-write-record guide record output)
  (ast:cad-inject "guide-metadata")
  (ast:cad-write-record output (list '(schema . 1) '(rule . 1) '(display-version . 8) (cons 'identity identity) (cons 'revision revision)
                                    (cons 'stitch-id stitch-id) (cons 'output-identity (cdr (assoc 5 (entget output))))
                                    (cons 'signature (ast:cad-output-signature output))) guide)
  (ast:cad-inject "output-metadata")
  (if (not (and (boundp 'ast:*cad-writing-set*) ast:*cad-writing-set*))
    (progn
      (ast:cad-update-markers state settings landmarks)
      (foreach old-output (ast:cad-set-outputs (list state))
        (if (not (equal output old-output))
          (ast:cad-require (entdel old-output) "Could not remove a superseded stitch output.")))))
  (setq corrected-count 0)
  (foreach interval (ast:cad-get 'intervals solution)
    (if (eq (ast:cad-get 'kind interval) 'corrected) (setq corrected-count (1+ corrected-count))))
  (list '(ok . T) (cons 'output output) (cons 'count (length (ast:cad-get 'openings solution)))
        (cons 'corrected-count corrected-count)
        (cons 'warnings (ast:cad-get 'warnings solution))))

(defun ast:cad-transaction-body (function arguments / sentinel)
  ;; A reversible sentinel guarantees this group's rollback cannot undo an earlier edit.
  (ast:cad-require (entmake '((0 . "POINT") (8 . "0") (10 0.0 0.0 0.0))) "BricsCAD could not start a change that can be undone.")
  (setq ast:*cad-mutated* T sentinel (entlast))
  (ast:cad-require (entdel sentinel) "BricsCAD could not prepare the drawing for an undoable change.")
  (apply function arguments))
(defun ast:cad-transaction (function arguments / ast:*cad-error* ast:*cad-mutated* ast:*cad-block-open* result old-echo cleanup)
  (cond
    ((= 0 (logand 1 (getvar "UNDOCTL"))) (list '(ok . nil) '(error . "Enable full Undo before editing a stitch line.")))
    ((/= 0 (logand 2 (getvar "UNDOCTL"))) (list '(ok . nil) '(error . "Change Undo from One to All before editing a stitch line.")))
    ((/= 0 (logand 8 (getvar "UNDOCTL"))) (list '(ok . nil) '(error . "Finish the active Undo group before editing a stitch line.")))
    (T
     (setq old-echo (getvar "CMDECHO")) (setvar "CMDECHO" 0)
     (vl-cmdf "_.UNDO" "_Begin")
     (setq result (vl-catch-all-apply 'ast:cad-transaction-body (list function arguments)))
     (if ast:*cad-block-open*
       (progn
         (setq cleanup (vl-catch-all-apply 'entmake (list '((0 . "ENDBLK")))))
         (if (or (null cleanup) (vl-catch-all-error-p cleanup))
           (setq ast:*cad-error* "BricsCAD could not finish the stitch block. Check the drawing before making further changes."))))
     (vl-cmdf "_.UNDO" "_End")
     (if (vl-catch-all-error-p result)
       (progn
         (if ast:*cad-mutated* (vl-cmdf "_.UNDO" "1"))
         (setq result (list '(ok . nil) (cons 'error (ast:cad-error-message result
           "BricsCAD could not save this change. Select the line again and retry."))))))
     (setvar "CMDECHO" old-echo) result)))

(defun ast:cad-attachments-valid-p (state landmarks / old-route new-route old-primitives new-primitives old-one new-one valid)
  (setq old-route (ast:cad-get 'attachment-route (ast:cad-get 'record state))
        new-route (ast:cad-get 'route state) valid T)
  (if (and landmarks old-route (not (ast:cad-get 'common-placement state)) (not (equal old-route new-route 1e-8)))
    (progn
      (setq old-primitives (ast:cad-get 'primitives old-route) new-primitives (ast:cad-get 'primitives new-route))
      (cond
        ((and (= 1 (length old-primitives)) (= 1 (length new-primitives))
              (eq 'line (ast:cad-get 'kind (car old-primitives)))
              (eq 'line (ast:cad-get 'kind (car new-primitives))))
          (setq old-one (mapcar '- (ast:cad-get 'b (car old-primitives)) (ast:cad-get 'a (car old-primitives)))
                new-one (mapcar '- (ast:cad-get 'b (car new-primitives)) (ast:cad-get 'a (car new-primitives))))
          (setq valid (> (apply '+ (mapcar '* old-one new-one)) 0.0)))
        ((and (= 1 (length old-primitives)) (= 1 (length new-primitives))
              (eq 'arc (ast:cad-get 'kind (car old-primitives)))
              (eq 'arc (ast:cad-get 'kind (car new-primitives)))
              (equal (ast:cad-get 'closed old-route) (ast:cad-get 'closed new-route))
              (> (* (ast:cad-get 'sweep (car old-primitives)) (ast:cad-get 'sweep (car new-primitives))) 0.0))
         (setq valid T))
        (T (setq valid nil))))) valid)

(defun ast:cad-run-generation (entity settings landmarks restore-placement / state solution output ranges)
  (setq state (ast:cad-read entity) ranges (if (ast:cad-get 'ok state) (ast:cad-resolve-ranges state settings)))
  (cond
    ((not (ast:cad-get 'ok state)) state)
    ((ast:cad-get 'error ranges) (list '(ok . nil) (cons 'error (ast:cad-get 'error ranges))))
    ((and (ast:cad-get 'output state)
          (not (equal (cdr (assoc 330 (entget (ast:cad-get 'guide state))))
                      (cdr (assoc 330 (entget (ast:cad-get 'output state)))))))
     (list '(ok . nil) '(error . "The guide and stitches are in different Model/Layout spaces. Move them into the same space before generating.")))
    ((not (ast:cad-attachments-valid-p state landmarks)) (list '(ok . nil) '(error . "The line changed. Remove its landmarks, then add them again.")))
    ((and (not restore-placement) (ast:cad-get 'placement-conflict state))
     (list '(ok . nil) '(error . "Stitches moved separately. Use Generate stitches in the palette to return them to the guide.")))
    ((or (not (ast:cad-layer-unlocked-p "AUTOSTITCH"))
         (not (ast:cad-layer-unlocked-p (cdr (assoc 8 (entget (ast:cad-get 'guide state))))))
         (and (setq output (ast:cad-get 'output state))
              (not (ast:cad-layer-unlocked-p (cdr (assoc 8 (entget output)))))))
     (list '(ok . nil) '(error . "Unlock the guide and AUTOSTITCH layers before Generate.")))
    (T
     (setq settings (ast:cad-get 'settings ranges))
     (setq solution (ast:g-solve (ast:cad-get 'route state) settings landmarks))
     (if (not (ast:cad-get 'ok solution)) solution
       (ast:cad-transaction 'ast:cad-write-inner (list state settings landmarks solution))))))
(defun ast:cad-generate (entity settings landmarks)
  (ast:cad-generate-dispatch entity settings landmarks nil))
(defun ast:cad-restore (entity settings landmarks)
  (ast:cad-generate-dispatch entity settings landmarks T))

(defun ast:cad-detach-inner (state / guide output record member)
  (setq guide (ast:cad-get 'guide state) output (ast:cad-get 'output state)
        record (vl-remove-if '(lambda (item) (eq (car item) 'link)) (ast:cad-get 'record state)))
  (foreach member (ast:cad-get 'members state)
    (setq record (vl-remove-if '(lambda (item) (eq (car item) 'link)) (ast:cad-record member)))
    (ast:cad-write-record member record nil))
  (ast:cad-inject "detach-guide")
  (ast:cad-write-record output (list '(schema . 1) '(rule . 1) '(detached . T)
                                    (cons 'identity (ast:cad-get 'identity record))) nil)
  (ast:cad-inject "detach-output")
  (list '(ok . T) (cons 'output output)))
(defun ast:cad-detach (entity / state output match-error)
  (setq state (ast:cad-read entity) output (ast:cad-get 'output state))
  (cond ((not (ast:cad-get 'ok state)) state)
        ((and (member 'ast:match-topology-error (atoms-family 0))
              (setq match-error (ast:match-topology-error entity)))
         (list '(ok . nil) (cons 'error match-error)))
        ((ast:cad-get 'missing-members state)
         (list '(ok . nil) '(error . "Remove missing lines before detaching this output.")))
        ((null output) (list '(ok . nil) '(error . "No linked stitches were found for this guide.")))
        ((or (vl-some '(lambda (member) (not (ast:cad-layer-unlocked-p (cdr (assoc 8 (entget member))))))
                     (ast:cad-get 'members state))
             (not (ast:cad-layer-unlocked-p (cdr (assoc 8 (entget output))))))
         (list '(ok . nil) '(error . "Unlock the guide and output layers before Detach.")))
        (T (ast:cad-transaction 'ast:cad-detach-inner (list state)))))

(defun ast:cad-save-inputs-inner (state settings landmarks / record preserve-baseline stitch-id owner)
  ;; Partial input repairs must not bless the unrepaired attachments.
  (setq preserve-baseline (or (ast:cad-get 'error (ast:cad-resolve-ranges state settings))
                              (and landmarks (not (ast:cad-attachments-valid-p state landmarks)))))
  (setq stitch-id (ast:cad-ensure-stitch-id (ast:cad-get 'guide state))
        owner (ast:cad-stitch-owner (ast:cad-get 'guide state))
        record (ast:cad-put 'stitch-id stitch-id (ast:cad-put 'stitch-owner
          (cdr (assoc 5 (entget owner))) (ast:cad-get 'record state))))
  (setq record (vl-remove-if '(lambda (item) (eq (car item) 'link)) record))
  (setq record (ast:cad-put 'schema (if (> (length (ast:cad-get 'members state)) 1) 2 1) record)
        record (ast:cad-put 'rule (if (> (length (ast:cad-get 'members state)) 1) 2 1) record)
        record (ast:cad-put 'factor (ast:cad-get 'factor state) record)
        record (ast:cad-put 'identity (if (> (length (ast:cad-get 'members state)) 1)
                  (ast:cad-get 'identity record)
                  (cdr (assoc 5 (entget (ast:cad-get 'guide state))))) record)
        record (ast:cad-put 'settings settings record)
        record (ast:cad-put 'landmarks landmarks record))
  (if (not preserve-baseline) (setq record (ast:cad-put 'attachment-route (ast:cad-get 'route state) record)))
  (ast:cad-write-record (ast:cad-get 'guide state) record (ast:cad-get 'output state))
  (ast:cad-update-markers state settings landmarks)
  (list '(ok . T)))
(defun ast:cad-save-inputs (entity settings landmarks / state ranges match-error)
  (setq state (ast:cad-read entity) ranges (if (ast:cad-get 'ok state) (ast:cad-resolve-ranges state settings)))
  (cond ((not (ast:cad-get 'ok state)) state)
        ((and (member 'ast:match-edit-error (atoms-family 0))
              (setq match-error (ast:match-edit-error entity)))
         (list '(ok . nil) (cons 'error match-error)))
        ((and landmarks (not (equal landmarks (ast:cad-get 'landmarks state)))
              (not (ast:cad-attachments-valid-p state (ast:cad-get 'landmarks state))))
         (list '(ok . nil) '(error . "The line changed. Remove its landmarks, then add them again.")))
        ((not (ast:cad-layer-unlocked-p (cdr (assoc 8 (entget (ast:cad-get 'guide state))))))
         (list '(ok . nil) '(error . "Unlock the guide layer before editing inputs.")))
        (T (ast:cad-transaction 'ast:cad-save-inputs-inner (list state (ast:cad-get 'settings ranges) landmarks)))))

(defun ast:cad-stitch-write (states hand / state)
  (foreach state states
    (ast:cad-save-inputs-inner state (ast:cad-put 'stitch-hand hand (ast:cad-get 'settings state))
      (ast:cad-get 'landmarks state)))
  (list '(ok . T)))
(defun ast:cad-set-stitch-inner (entity hand / selected states state member match-error)
  (ast:cad-require (member hand '(1 -1)) "Choose Obverse or Reverse for the stitch lean.")
  (setq selected (ast:cad-read-inner entity))
  (ast:cad-require (not (ast:cad-get 'missing-members selected))
    "A connected guide is missing. Use Remove missing lines before changing stitch lean.")
  (if (member 'ast:match-edit-error (atoms-family 0))
    (setq match-error (ast:match-edit-error entity)))
  (ast:cad-require (null match-error) match-error)
  (foreach member (ast:cad-get 'members selected)
    (setq state (ast:cad-read-base member))
    (ast:cad-require (ast:cad-layer-unlocked-p (cdr (assoc 8 (entget member))))
      "Unlock the guide layers before changing stitch lean.")
    (setq states (append states (list state))))
  (ast:cad-transaction 'ast:cad-stitch-write (list states hand)))
(defun ast:cad-set-stitch (entity hand)
  (ast:cad-catch 'ast:cad-set-stitch-inner (list entity hand)))

;;; A connected set owns one output. Source-specific inputs stay on each source.
(defun ast:cad-set-states (members selected settings landmarks / states state member ranges)
  (setq states nil)
  (foreach member members
    (setq state (ast:cad-read-base member))
    (if (equal member selected)
      (setq state (ast:cad-put 'settings settings (ast:cad-put 'landmarks landmarks state))))
    (setq ranges (ast:cad-resolve-ranges state (ast:cad-get 'settings state)))
    (ast:cad-require (not (ast:cad-get 'error ranges)) (ast:cad-get 'error ranges))
    (setq state (ast:cad-put 'settings (ast:cad-get 'settings ranges) state)
          states (append states (list state))))
  states)

(defun ast:cad-set-paths (states / paths index state)
  (setq index 0 paths nil)
  (foreach state states
    (setq paths (append paths (list (list (cons 'id index)
      (cons 'route (ast:cad-get 'route state)) (cons 'settings (ast:cad-get 'settings state))
      (cons 'landmarks (ast:cad-get 'landmarks state))))) index (1+ index)))
  paths)

(defun ast:cad-set-check (states restore-placement / first-state owner factor profile state guide output)
  (setq first-state (car states) owner (cdr (assoc 330 (entget (ast:cad-get 'guide first-state))))
        factor (ast:cad-get 'factor first-state) profile (ast:cad-get 'settings first-state))
  (ast:cad-require (ast:cad-layer-unlocked-p "AUTOSTITCH") "Unlock the AUTOSTITCH layer before Generate.")
  (foreach state states
    (setq guide (ast:cad-get 'guide state) output (ast:cad-get 'output state))
    (ast:cad-require (equal owner (cdr (assoc 330 (entget guide)))) "Both stitch lines must be in the same Model/Layout space before connecting them.")
    (ast:cad-require (equal factor (ast:cad-get 'factor state) 1e-10) "These stitch lines have different saved units. Recreate them using the same drawing units before connecting.")
    (ast:cad-require (ast:n-profile-same profile (ast:cad-get 'settings state))
                     "These lines have different saved tool settings. Their tool settings must match before connecting.")
    (ast:cad-require (ast:cad-attachments-valid-p state (ast:cad-get 'landmarks state))
                     "A connected line changed shape. Select that line, remove its landmarks and add them again.")
    (ast:cad-require (or restore-placement (not (ast:cad-get 'placement-conflict state)))
                     "Stitches moved separately. Use Generate stitches to return them to the guide before connecting lines.")
    (ast:cad-require (ast:cad-layer-unlocked-p (cdr (assoc 8 (entget guide))))
                     "Unlock the layers containing the connected guide lines before generating.")
    (if output
      (progn
        (ast:cad-require (equal owner (cdr (assoc 330 (entget output)))) "A stitch block is in a different Model/Layout space from its guides. Move them into the same space.")
        (ast:cad-require (ast:cad-layer-unlocked-p (cdr (assoc 8 (entget output))))
                         "Unlock the layers containing the connected stitch blocks before generating."))))
  T)

(defun ast:cad-pending-output-p (output members / record)
  (and output (entget output) (setq record (ast:cad-record output))
    (vl-some '(lambda (member) (and member (entget member)
      (member member (ast:cad-get 'pending-members record)))) members)))

(defun ast:cad-set-outputs (states / outputs state output)
  (setq outputs nil)
  (foreach state states
    (if (and (setq output (ast:cad-get 'output state)) (not (member output outputs)))
      (setq outputs (append outputs (list output))))
    (foreach output (if (assoc 'retained-outputs state) (ast:cad-get 'retained-outputs state)
                       (ast:cad-get 'retained-outputs (ast:cad-get 'record state)))
      (if (and (ast:cad-pending-output-p output (ast:cad-get 'members state))
               (not (member output outputs))) (setq outputs (append outputs (list output))))))
  outputs)

(defun ast:cad-write-guide-set-inner (states connections / primary members identity stitch-id state guide record settings index outputs output retained)
  ;; Topology is an input. Keep previous output links and snapshots until Generate succeeds.
  (setq primary (ast:cad-get 'guide (car states))
        members (mapcar '(lambda (state) (ast:cad-get 'guide state)) states)
        identity (cdr (assoc 5 (entget primary))) outputs (ast:cad-set-outputs states)
        output (vl-some '(lambda (candidate)
          (if (equal (cdr (assoc 2 (entget candidate))) (ast:cad-get 'stitch-id (ast:cad-record primary))) candidate)) outputs))
  (if (null output) (setq output (ast:cad-get 'output (car states))))
  (setq stitch-id (ast:cad-assigned-id primary output) index 0)
  (foreach state states
    (setq guide (ast:cad-get 'guide state)
          settings (ast:cad-rebase-ranges (ast:cad-get 'settings state) (ast:cad-get 'route state))
          record (vl-remove-if '(lambda (item)
            (member (car item) '(schema rule identity stitch-id stitch-owner primary members connections link topology-pending retained-outputs settings landmarks factor attachment-route)))
            (ast:cad-get 'record state))
          record (append (list (cons 'schema (if (> (length members) 1) 2 1))
            (cons 'rule (if (> (length members) 1) 2 1)) (cons 'identity identity)
            (cons 'stitch-id stitch-id) (cons 'stitch-owner identity) '(topology-pending . T)
            (cons 'retained-outputs outputs)
            (cons 'settings settings) (cons 'landmarks (ast:cad-get 'landmarks state))
            (cons 'factor (ast:cad-get 'factor state)) (cons 'attachment-route (ast:cad-get 'route state))) record))
    (if (> (length members) 1)
      (setq record (append record (list (cons 'primary primary) (cons 'members members)
        (cons 'connections connections)))))
    (ast:cad-write-record guide record (if (equal guide primary) output (ast:cad-get 'output state)))
    (ast:cad-inject (strcat "guide-set-metadata-" (itoa index)))
    (setq index (1+ index)))
  (foreach retained outputs
    (setq record (ast:cad-record retained))
    (ast:cad-write-record retained
      (ast:cad-put 'pending-members members (vl-remove-if '(lambda (item) (eq (car item) 'link)) record))
      (ast:cad-get 'link record)))
  (foreach state states
    (ast:cad-update-markers state (ast:cad-rebase-ranges (ast:cad-get 'settings state) (ast:cad-get 'route state))
      (ast:cad-get 'landmarks state)))
  (list '(ok . T) (cons 'members members)))

(defun ast:cad-write-set-inner (states connections solution / ast:*cad-writing-set* result primary members output revision identity stitch-id state record settings guide index old-outputs old-output)
  (setq ast:*cad-writing-set* T primary (ast:cad-get 'guide (car states))
        members (mapcar '(lambda (state) (ast:cad-get 'guide state)) states)
        old-outputs (ast:cad-set-outputs states)
        result (ast:cad-write-inner (car states) (ast:cad-get 'settings (car states))
                    (ast:cad-get 'landmarks (car states)) solution)
        output (ast:cad-get 'output result) record (ast:cad-record primary)
        revision (ast:cad-get 'revision record) identity (ast:cad-get 'identity record)
        stitch-id (ast:cad-get 'stitch-id record) index 0)
  (foreach state states
    (setq guide (ast:cad-get 'guide state)
          settings (ast:cad-rebase-ranges (ast:cad-get 'settings state) (ast:cad-get 'route state))
          record (list '(schema . 2) '(rule . 2) (cons 'identity identity) (cons 'revision revision)
            (cons 'stitch-id stitch-id) (cons 'stitch-owner identity)
            (cons 'settings settings) (cons 'landmarks (ast:cad-get 'landmarks state))
            (cons 'attachment-route (ast:cad-get 'route state)) (cons 'generated-route (ast:cad-get 'route state))
            (cons 'generated-settings settings) (cons 'generated-landmarks (ast:cad-get 'landmarks state))
            (cons 'factor (ast:cad-get 'factor state)) (cons 'primary primary)))
    (if (= index 0) (setq record (append record (list (cons 'connections connections) (cons 'members members)))))
    (ast:cad-write-record guide record output)
    (ast:cad-inject (strcat "member-metadata-" (itoa index)))
    (setq index (1+ index)))
  (ast:cad-write-record output (list '(schema . 2) '(rule . 2) '(display-version . 8) '(junction-version . 1) (cons 'identity identity) (cons 'revision revision)
                                    (cons 'stitch-id stitch-id)
                                    (cons 'output-identity (cdr (assoc 5 (entget output))))
                                    (cons 'signature (ast:cad-output-signature output))
                                    (cons 'members members) (cons 'connections (ast:cad-backup-connections connections))) primary)
  (ast:cad-inject "set-output-metadata")
  (foreach state states
    (ast:cad-update-markers state (ast:cad-rebase-ranges (ast:cad-get 'settings state) (ast:cad-get 'route state))
                           (ast:cad-get 'landmarks state)))
  (foreach old-output old-outputs
    (if (not (equal output old-output))
      (progn
        (ast:cad-require (entdel old-output) "Could not remove a superseded stitch output.")
        (ast:cad-inject "retired-output"))))
  (append result (list (cons 'members members))))

(defun ast:cad-resolve-set (states connections / paths result)
  (setq paths (ast:cad-set-paths states)
        result (ast:g-resolve-connections paths connections))
  (ast:cad-require (ast:cad-get 'ok result) (ast:cad-get 'error result))
  (setq connections (ast:cad-get 'connections result)
        result (ast:g-solve-set paths connections))
  (ast:cad-require (ast:cad-get 'ok result) (ast:cad-get 'error result))
  (list (cons 'connections connections) (cons 'solution result)))

(defun ast:cad-generate-set-inner (state settings landmarks restore-placement / states solved)
  (setq states (ast:cad-set-states (ast:cad-get 'members state) (ast:cad-get 'guide state) settings landmarks))
  (ast:cad-set-check states restore-placement)
  (setq solved (ast:cad-resolve-set states (ast:cad-get 'connections state)))
  (ast:cad-transaction 'ast:cad-write-set-inner
    (list states (ast:cad-get 'connections solved) (ast:cad-get 'solution solved))))

(defun ast:cad-catch (function arguments / ast:*cad-error* result)
  (setq result (vl-catch-all-apply function arguments))
  (if (vl-catch-all-error-p result)
    (list '(ok . nil) (cons 'error (ast:cad-error-message result
      "Could not complete this stitching action. Select the line again and retry."))) result))

(defun ast:cad-generate-dispatch (entity settings landmarks restore-placement / state)
  (setq state (ast:cad-read entity))
  (cond ((not (ast:cad-get 'ok state)) state)
        ((and (member 'ast:match-info (atoms-family 0))
              (ast:cad-get 'active (ast:match-info entity)))
         (ast:match-generate entity settings landmarks restore-placement))
        ((ast:cad-get 'missing-members state)
         (list '(ok . nil) '(error . "A connected stitch line was deleted. Remove missing lines before Generate.")))
        ((> (length (ast:cad-get 'members state)) 1)
         (ast:cad-catch 'ast:cad-generate-set-inner (list state settings landmarks restore-placement)))
        (T (ast:cad-run-generation entity settings landmarks restore-placement))))

(defun ast:cad-remap-connections (connections old-members new-members / answer node incidences incidence member index)
  (setq answer nil)
  (foreach node connections
    (setq incidences nil)
    (foreach incidence (ast:cad-get 'incidences node)
      (setq member (nth (ast:cad-get 'path incidence) old-members)
            index (vl-position member new-members))
      (ast:cad-require (numberp index) "A connected line is missing. Use Remove missing lines, then reconnect any remaining lines that should meet.")
      (setq incidences (append incidences (list (ast:cad-put 'path index incidence)))))
    (setq answer (append answer (list (ast:cad-put 'incidences incidences node)))))
  answer)

(defun ast:cad-pick-connection (candidates point / best best-distance candidate distance-value tied)
  (foreach candidate candidates
    (setq distance-value (distance point (ast:cad-get 'point candidate)))
    (cond ((or (null best-distance) (< distance-value (- best-distance 1e-8)))
           (setq best candidate best-distance distance-value tied nil))
          ((equal distance-value best-distance 1e-8) (setq tied T))))
  (ast:cad-require best "These lines do not meet or cross. Extend or move a guide so they meet, then connect them.")
  (ast:cad-require (not tied) "That pick is equally close to two intersections. Pick nearer the intended one.")
  best)

(defun ast:cad-number-connections (connections / index answer node)
  (setq index 0 answer nil)
  (foreach node connections
    (setq answer (append answer (list (ast:cad-put 'id index node))) index (1+ index)))
  answer)

(defun ast:cad-merge-connection (connections node / previous incidence incidences item same-point answer)
  (setq previous (vl-some '(lambda (item)
    (if (equal (ast:cad-get 'point item) (ast:cad-get 'point node) 1e-8) item)) connections))
  (if previous
    (progn
      (setq incidences (ast:cad-get 'incidences previous))
      (setq same-point (vl-remove-if-not '(lambda (item)
        (equal (ast:cad-get 'point item) (ast:cad-get 'point node) 1e-8)) connections))
      (foreach item (append same-point (list node))
       (foreach incidence (ast:cad-get 'incidences item)
        (if (not (vl-some '(lambda (item)
          (and (= (ast:cad-get 'path item) (ast:cad-get 'path incidence))
               (= (ast:cad-get 'primitive item) (ast:cad-get 'primitive incidence)))) incidences))
          (setq incidences (append incidences (list incidence))))))
      (setq answer nil)
      (foreach item connections
        (cond ((equal item previous) (setq answer (append answer (list (ast:cad-put 'incidences incidences previous)))))
              ((not (member item same-point)) (setq answer (append answer (list item))))))
      answer)
    (append connections (list node))))

(defun ast:cad-connect-context (selected other-state / members other-members member connections states resolved)
  (ast:cad-require (not (or (ast:cad-get 'missing-members selected) (ast:cad-get 'missing-members other-state)))
                   "Remove missing lines from the existing stitches before connecting another line.")
  (setq members (ast:cad-get 'members selected) other-members (ast:cad-get 'members other-state)
        connections (ast:cad-get 'connections selected))
  (foreach member other-members
    (if (not (member member members)) (setq members (append members (list member)))))
  (if (not (equal (ast:cad-get 'primary selected) (ast:cad-get 'primary other-state)))
    (setq connections (append connections (ast:cad-remap-connections
      (ast:cad-get 'connections other-state) other-members members))))
  (setq states (ast:cad-set-states members nil nil nil)
        resolved (ast:g-resolve-connections (ast:cad-set-paths states) connections))
  (ast:cad-require (ast:cad-get 'ok resolved) (ast:cad-get 'error resolved))
  (list (cons 'states states) (cons 'members members) (cons 'connections (ast:cad-get 'connections resolved))))

(defun ast:cad-all-connections (states connections / members tail rest first-state second-state candidates node pending merged ranges state range)
  (setq members (mapcar '(lambda (state) (ast:cad-get 'guide state)) states) tail states pending nil)
  (foreach state states
    (setq range (ast:g-range (ast:cad-get 'primitives (ast:cad-get 'route state))
                  (ast:cad-get 'landmarks state) (ast:cad-get 'settings state)
                  (ast:cad-get 'closed (ast:cad-get 'route state))))
    (ast:cad-require (ast:cad-get 'ok range) (ast:cad-get 'error range))
    (setq ranges (cons (cons (ast:cad-get 'guide state) (ast:cad-get 'primitives range)) ranges)))
  (while tail
    (setq first-state (car tail) rest (cdr tail))
    (while rest
      (setq second-state (car rest)
            candidates (ast:g-connect-candidates (ast:cad-get 'route first-state) (ast:cad-get 'route second-state)))
      (ast:cad-require (ast:cad-get 'ok candidates) (ast:cad-get 'error candidates))
      (foreach node (ast:cad-remap-connections (ast:cad-get 'connections candidates)
                (list (ast:cad-get 'guide first-state) (ast:cad-get 'guide second-state)) members)
        (if (and (vl-some '(lambda (primitive) (ast:g-point-on primitive (ast:cad-get 'point node)))
                         (cdr (assoc (ast:cad-get 'guide first-state) ranges)))
                 (vl-some '(lambda (primitive) (ast:g-point-on primitive (ast:cad-get 'point node)))
                         (cdr (assoc (ast:cad-get 'guide second-state) ranges))))
          (progn
            (setq merged (ast:cad-merge-connection connections node))
            (if (not (equal merged connections))
              (setq pending (ast:cad-merge-connection pending node) connections merged)))))
      (setq rest (cdr rest)))
    (setq tail (cdr tail)))
  (list '(ok . T) (cons 'count (length pending)) (cons 'candidates pending)
        (cons 'connections (ast:cad-number-connections connections))))

(defun ast:cad-connect-preview-inner (entity other / selected other-state context result)
  (setq selected (ast:cad-read-inner entity) other-state (ast:cad-read-inner other))
  (ast:cad-require (not (equal (ast:cad-get 'guide selected) (ast:cad-get 'guide other-state)))
                   "That is the same stitch line. Select another line to connect.")
  (setq context (ast:cad-connect-context selected other-state)
        result (ast:cad-all-connections (ast:cad-get 'states context) (ast:cad-get 'connections context)))
  (append result (list (cons 'members (ast:cad-get 'members context)))))

(defun ast:cad-connect-preview (entity other)
  (ast:cad-catch 'ast:cad-connect-preview-inner (list entity other)))

(defun ast:cad-connect-inner (entity other world-point settings landmarks / selected other-state members states candidates candidate node connections solved context merged match-error)
  (if (member 'ast:match-topology-error (atoms-family 0))
    (foreach candidate (list entity other)
      (setq match-error (ast:match-topology-error candidate))
      (ast:cad-require (null match-error) match-error)))
  (setq selected (ast:cad-read-inner entity) other-state (ast:cad-read-inner other))
  (ast:cad-require (not (equal (ast:cad-get 'guide selected) (ast:cad-get 'guide other-state)))
                   "That is the same stitch line. Select another line to connect.")
  (setq context (ast:cad-connect-context selected other-state)
        members (ast:cad-get 'members context) connections (ast:cad-get 'connections context))
  (setq states (ast:cad-set-states members (ast:cad-get 'guide selected) settings landmarks))
  (ast:cad-set-check states nil)
  (if world-point
    (progn
      (setq candidates (ast:g-connect-candidates (ast:cad-get 'route selected) (ast:cad-get 'route other-state)))
      (ast:cad-require (ast:cad-get 'ok candidates) (ast:cad-get 'error candidates))
      (setq node (ast:cad-pick-connection (ast:cad-get 'connections candidates)
                    (ast:cad-xy world-point (ast:cad-get 'factor selected)))
            node (car (ast:cad-remap-connections (list node)
                     (list (ast:cad-get 'guide selected) (ast:cad-get 'guide other-state)) members))
            merged (ast:cad-merge-connection connections node))
      (ast:cad-require (not (equal merged connections)) "These lines are already connected at this point.")
      (setq connections merged))
    (progn
      (setq candidates (ast:cad-all-connections states connections))
      (ast:cad-require (> (ast:cad-get 'count candidates) 0) "There are no unconnected meeting or crossing points between these lines.")
      (setq connections (ast:cad-get 'connections candidates))))
  (setq connections (ast:cad-number-connections connections))
  (if (and (boundp 'ast:*cad-defer-generation*) ast:*cad-defer-generation*)
    (ast:cad-transaction 'ast:cad-write-guide-set-inner (list states connections))
    (progn
      (setq solved (ast:cad-resolve-set states connections))
      (ast:cad-transaction 'ast:cad-write-set-inner
        (list states (ast:cad-get 'connections solved) (ast:cad-get 'solution solved))))))

(defun ast:cad-connect (entity other world-point settings landmarks)
  (ast:cad-catch 'ast:cad-connect-inner (list entity other world-point settings landmarks)))

(defun ast:cad-connect-guides (entity other world-point settings landmarks / ast:*cad-defer-generation*)
  (setq ast:*cad-defer-generation* T)
  (ast:cad-connect entity other world-point settings landmarks))

(defun ast:cad-without-path-connections (connections index / answer node incidences)
  (setq answer nil)
  (foreach node connections
    (setq incidences (vl-remove-if '(lambda (incidence) (= index (ast:cad-get 'path incidence)))
                                   (ast:cad-get 'incidences node)))
    (if (> (length incidences) 1)
      (setq answer (append answer (list (ast:cad-put 'incidences incidences node))))))
  answer)

(defun ast:cad-without-missing-connections (connections members / answer node incidences)
  (foreach node connections
    (setq incidences (vl-remove-if-not '(lambda (incidence)
      (and (nth (ast:cad-get 'path incidence) members)
           (entget (nth (ast:cad-get 'path incidence) members)))) (ast:cad-get 'incidences node)))
    (if (> (length incidences) 1)
      (setq answer (append answer (list (ast:cad-put 'incidences incidences node)))))) answer)

(defun ast:cad-components (count connections / remaining index groups component changed node indexes item)
  (setq index 0 remaining nil groups nil)
  (repeat count (setq remaining (append remaining (list index)) index (1+ index)))
  (while remaining
    (setq component (list (car remaining)) changed T)
    (while changed
      (setq changed nil)
      (foreach node connections
        (setq indexes (mapcar '(lambda (incidence) (ast:cad-get 'path incidence)) (ast:cad-get 'incidences node)))
        (if (vl-some '(lambda (item) (member item component)) indexes)
          (foreach item indexes
            (if (not (member item component)) (setq component (append component (list item)) changed T))))))
    (setq remaining (vl-remove-if '(lambda (item) (member item component)) remaining)
          groups (append groups (list component))))
  groups)

(defun ast:cad-write-components-inner (plans / results plan states result)
  (setq results nil)
  (foreach plan plans
    (setq states (ast:cad-get 'states plan))
    (if (and (boundp 'ast:*cad-defer-generation*) ast:*cad-defer-generation*)
      (setq result (ast:cad-write-guide-set-inner states (ast:cad-get 'connections plan)))
    (if (> (length states) 1)
      (setq result (ast:cad-write-set-inner states (ast:cad-get 'connections plan) (ast:cad-get 'solution plan)))
      (setq result (ast:cad-write-inner (car states) (ast:cad-get 'settings (car states))
                      (ast:cad-get 'landmarks (car states)) (ast:cad-get 'solution plan)))))
    (setq results (append results (list result)))
    (ast:cad-inject "disconnected-component"))
  (if (and (boundp 'ast:*cad-repairing-missing*) ast:*cad-repairing-missing*
           (member 'ast:markers-prune-missing (atoms-family 0)))
    (progn (ast:markers-prune-missing) (ast:cad-inject "missing-markers")))
  (list '(ok . T) (cons 'results results)))

(defun ast:cad-disconnect-inner (entity / selected members original-members index connections states groups group group-states group-members group-connections node plans solved solution claimed-outputs state outputs group-outputs output owner match-error ast:*cad-repairing-missing*)
  (if (member 'ast:match-topology-error (atoms-family 0))
    (progn (setq match-error (ast:match-topology-error entity))
      (ast:cad-require (null match-error) match-error)))
  (setq selected (ast:cad-read-inner entity) members (ast:cad-get 'members selected)
        index (vl-position (ast:cad-get 'guide selected) members)
        ast:*cad-repairing-missing* (ast:cad-get 'missing-members selected))
  (ast:cad-require (> (length members) 1) "This stitch line is not connected to another line.")
  (if (ast:cad-get 'missing-members selected)
    (progn
      (setq original-members members
            members (vl-remove-if-not '(lambda (member) (and member (entget member))) members)
            connections (ast:cad-remap-connections
              (ast:cad-without-missing-connections (ast:cad-get 'connections selected) original-members)
              original-members members)))
    (setq connections (ast:cad-without-path-connections (ast:cad-get 'connections selected) index)))
  (setq states (ast:cad-set-states members nil nil nil)
        groups (ast:cad-components (length members) connections) plans nil claimed-outputs nil
        outputs (ast:cad-set-outputs states))
  (ast:cad-set-check states nil)
  (foreach group groups
    (setq group-states nil group-members nil group-connections nil)
    (foreach index group
      (setq state (nth index states))
      ;; A retained output belongs to one component; independent old outputs keep their owners.
      (if (member (ast:cad-get 'output state) claimed-outputs) (setq state (ast:cad-put 'output nil state)))
      (setq group-states (append group-states (list state))
            group-members (append group-members (list (nth index members)))))
    (setq group-outputs nil)
    (foreach output outputs
      (setq owner (ast:cad-get 'link (ast:cad-record output)))
      (if (and (not (member output claimed-outputs))
               (or (member owner group-members) (not (member owner members))))
        (setq group-outputs (append group-outputs (list output)))))
    (setq group-states (mapcar '(lambda (state)
      (ast:cad-put 'retained-outputs group-outputs
        (if (member (ast:cad-get 'output state) group-outputs) state (ast:cad-put 'output nil state)))) group-states))
    (foreach node connections
      (if (member (ast:cad-get 'path (car (ast:cad-get 'incidences node))) group)
        (setq group-connections (append group-connections (list node)))))
    (setq group-connections (ast:cad-remap-connections group-connections members group-members))
    (if (and (boundp 'ast:*cad-defer-generation*) ast:*cad-defer-generation*)
      (setq solved (list (cons 'connections group-connections)))
    (if (> (length group-states) 1)
      (setq solved (ast:cad-resolve-set group-states group-connections))
      (progn
        (setq state (car group-states) solution (ast:g-solve (ast:cad-get 'route state)
                   (ast:cad-get 'settings state) (ast:cad-get 'landmarks state)))
        (ast:cad-require (ast:cad-get 'ok solution) (ast:cad-get 'error solution))
        (setq solved (list (cons 'solution solution))))))
    (setq plans (append plans (list (append (list (cons 'states group-states)) solved)))
          claimed-outputs (append claimed-outputs group-outputs)))
  (ast:cad-transaction 'ast:cad-write-components-inner (list plans)))

(defun ast:cad-disconnect (entity)
  (ast:cad-catch 'ast:cad-disconnect-inner (list entity)))

(defun ast:cad-disconnect-guides (entity / ast:*cad-defer-generation*)
  (setq ast:*cad-defer-generation* T)
  (ast:cad-disconnect entity))
(princ)
