;;; Pure analytic geometry. Distances are mm; angles are radians, WCS XY y-up.
;;; Default slit lean is positive relative to the traversal tangent.
(defun ast:g-get (key record fallback / pair)
  (if (setq pair (assoc key record)) (cdr pair) fallback))
(defun ast:g-error (message) (list (cons 'ok nil) (cons 'error message)))
(defun ast:g-add (aa bb) (list (+ (car aa) (car bb)) (+ (cadr aa) (cadr bb))))
(defun ast:g-sub (aa bb) (list (- (car aa) (car bb)) (- (cadr aa) (cadr bb))))
(defun ast:g-mul (aa factor) (list (* (car aa) factor) (* (cadr aa) factor)))
(defun ast:g-dot (aa bb) (+ (* (car aa) (car bb)) (* (cadr aa) (cadr bb))))
(defun ast:g-cross (aa bb) (- (* (car aa) (cadr bb)) (* (cadr aa) (car bb))))
(defun ast:g-norm (aa) (sqrt (ast:g-dot aa aa)))
(defun ast:g-dist (aa bb) (ast:g-norm (ast:g-sub aa bb)))
(defun ast:g-left (aa) (list (- (cadr aa)) (car aa)))
(defun ast:g-clamp (value low high) (max low (min high value)))
(defun ast:g-finite (value) (and (numberp value) (= value value) (< (abs value) 1.0e100)))
(defun ast:g-pointp (value) (and (listp value) (= (length value) 2) (ast:g-finite (car value)) (ast:g-finite (cadr value))))
(defun ast:g-tol (value) (* 1.4210854715202004e-14 (max 1.0 (abs value))))
(defun ast:g-near (aa bb) (<= (abs (- aa bb)) (ast:g-tol (max (abs aa) (abs bb)))))
(defun ast:g-floor (value / whole) (setq whole (fix value)) (if (< value whole) (1- whole) whole))
(defun ast:g-ceil (value) (- (ast:g-floor (- value))))
(defun ast:g-ceil-near (value) (ast:g-ceil (- value (ast:g-tol value))))
(defun ast:g-floor-near (value) (ast:g-floor (+ value (ast:g-tol value))))
(defun ast:g-asin (value) (atan value (sqrt (max 0.0 (- 1.0 (* value value))))))
(defun ast:g-sign (value) (if (< value 0.0) -1.0 1.0))

;;; Shared bounded count selection for lines and circles. No interval-count search.
(defun ast:g-fit (total pitch radius protect-start protect-end corrections / nominal minimum maximum extension contraction low high ideal count-a count-b residual-a residual-b ka kb changed lower upper symmetric-low symmetric-high step below candidates best deviation adjusted chord block idx gaps advances residual candidate)
  (cond
    ((or (< total 0.0) (<= pitch 0.0) (< protect-start 0) (< protect-end 0)) (ast:g-error "Cannot calculate stitching from this length or pitch. Check the line and enter a positive pitch."))
    ((and radius (> pitch (* 2.0 radius))) (ast:g-error "The pitch is too large for this curve. Reduce the pitch or increase the curve radius."))
    ((= total 0.0) (if (> (+ protect-start protect-end) 0) (ast:g-error "There is no room for the required stitch spacing here. Move the endpoint, landmark or junction.") (list '(ok . T) '(count . 0) '(changed . 0) '(gaps) '(advances))))
    (T
      (setq nominal (if radius (* 2.0 (ast:g-asin (/ pitch (* 2.0 radius)))) pitch)
            minimum (if radius (* 2.0 (ast:g-asin (/ (* pitch (if corrections 0.9 1.0)) (* 2.0 radius)))) (* pitch (if corrections 0.9 1.0)))
            maximum (if radius (* 2.0 (ast:g-asin (min 1.0 (/ (* pitch (if corrections 1.1 1.0)) (* 2.0 radius))))) (* pitch (if corrections 1.1 1.0)))
            extension (- maximum nominal) contraction (- nominal minimum)
            low (max 1 (+ protect-start protect-end) (ast:g-ceil-near (/ (+ total (* (+ protect-start protect-end) extension)) maximum)))
            high (ast:g-floor-near (/ (- total (* (+ protect-start protect-end) contraction)) minimum)))
      ;; An integer interval count must satisfy both fixed anchors, protected
      ;; nominal intervals, and the allowed pitch bounds (normally +/-10%).
      (cond
        ((> low high) (ast:g-error "Stitches cannot fit this section at the chosen pitch. Change the pitch or adjust an endpoint, landmark or junction."))
        ((> low 2000) (ast:g-error "This section needs more than 2000 stitches. Split the guide into shorter stitch lines."))
        (T
          (setq ideal (/ total nominal)
                count-a (ast:g-clamp (ast:g-floor-near ideal) low high)
                count-b (ast:g-clamp (ast:g-ceil-near ideal) low high)
                residual-a (- total (* count-a nominal)) residual-b (- total (* count-b nominal))
                ka (ast:g-required-k residual-a total extension contraction)
                kb (ast:g-required-k residual-b total extension contraction)
                changed (min ka kb))
          (if (> changed high)
            (ast:g-error "This section needs more spacing adjustment than allowed. Change the pitch or the section length.")
            (progn
              (setq lower (max low (ast:g-ceil-near (/ (- total (* changed extension)) nominal)))
                    upper (min high (ast:g-floor-near (/ (+ total (* changed contraction)) nominal))) step 1)
              (if (> changed 0)
                (progn
                  (setq symmetric-low (max lower (+ changed (* 2 (max protect-start protect-end))))
                        symmetric-high upper)
                  (if (/= (rem (- symmetric-low changed) 2) 0) (setq symmetric-low (1+ symmetric-low)))
                  (if (/= (rem (- symmetric-high changed) 2) 0) (setq symmetric-high (1- symmetric-high)))
                  (if (<= symmetric-low symmetric-high) (setq lower symmetric-low upper symmetric-high step 2))))
              (setq below (+ lower (* step (ast:g-floor-near (/ (- ideal lower) step))))
                    candidates (list (ast:g-clamp below lower upper) (ast:g-clamp (+ below step) lower upper)))
              (foreach count-a candidates
                (if (<= changed (- count-a protect-start protect-end))
                  (progn
                    (setq residual (- total (* count-a nominal))
                          adjusted (if (= changed 0) nominal (+ nominal (/ residual changed)))
                          chord (if radius (* 2.0 radius (sin (/ adjusted 2.0))) adjusted)
                          deviation (abs (- (/ chord pitch) 1.0)))
                    (if (or (null best) (< deviation (- (car best) (ast:g-tol deviation))) (and (ast:g-near deviation (car best)) (< count-a (cadr best))))
                      (setq best (list deviation count-a adjusted chord))))))
              (if (or (null best) (> (cadr best) 2000))
                (ast:g-error (if best "This section needs more than 2000 stitches. Split the guide into shorter stitch lines." "Required spacing near landmarks or junctions leaves no room to adjust stitches. Move those points or change the pitch."))
                (progn
                  (setq count-a (cadr best) adjusted (caddr best) chord (cadddr best)
                        block (ast:g-clamp (ast:g-floor (+ (/ (- count-a changed) 2.0) 0.5)) protect-start (- count-a protect-end changed)) idx 0)
                  (repeat count-a
                    (setq candidate (and (> changed 0) (>= idx block) (< idx (+ block changed)))
                          gaps (cons (if candidate chord pitch) gaps)
                          advances (cons (if candidate adjusted nominal) advances) idx (1+ idx)))
                  (list '(ok . T) (cons 'count count-a) (cons 'changed changed) (cons 'block-start block)
                        (cons 'gaps (reverse gaps)) (cons 'advances (reverse advances))))))))))))
(defun ast:g-required-k (residual total extension contraction / capacity)
  (if (<= (abs residual) (ast:g-tol total)) 0
    (progn (setq capacity (if (> residual 0) extension contraction))
      (if (> capacity 0) (ast:g-ceil-near (/ (abs residual) capacity)) 100000001))))
(defun ast:g-fit-line (distance pitch protect-start protect-end corrections)
  (ast:g-fit distance pitch nil protect-start protect-end corrections))
(defun ast:g-fit-arc (radius sweep pitch protect-start protect-end corrections)
  (ast:g-fit (abs sweep) pitch radius protect-start protect-end corrections))

(defun ast:g-length (primitive)
  (if (= (cdr (assoc 'kind primitive)) 'line)
    (ast:g-dist (cdr (assoc 'a primitive)) (cdr (assoc 'b primitive)))
    (* (cdr (assoc 'radius primitive)) (abs (cdr (assoc 'sweep primitive))))))
(defun ast:g-point (primitive station / angle radius)
  (if (= (cdr (assoc 'kind primitive)) 'line)
    (ast:g-add (cdr (assoc 'a primitive)) (ast:g-mul (ast:g-sub (cdr (assoc 'b primitive)) (cdr (assoc 'a primitive))) (/ station (ast:g-length primitive))))
    (progn (setq radius (cdr (assoc 'radius primitive)) angle (+ (cdr (assoc 'start-angle primitive)) (* (ast:g-sign (cdr (assoc 'sweep primitive))) (/ station radius))))
      (ast:g-add (cdr (assoc 'center primitive)) (list (* radius (cos angle)) (* radius (sin angle)))))))
(defun ast:g-tangent (primitive station / angle)
  (if (= (cdr (assoc 'kind primitive)) 'line)
    (ast:g-mul (ast:g-sub (cdr (assoc 'b primitive)) (cdr (assoc 'a primitive))) (/ 1.0 (ast:g-length primitive)))
    (progn (setq angle (+ (cdr (assoc 'start-angle primitive)) (* (ast:g-sign (cdr (assoc 'sweep primitive))) (/ station (cdr (assoc 'radius primitive))))))
      (ast:g-mul (list (- (sin angle)) (cos angle)) (ast:g-sign (cdr (assoc 'sweep primitive)))))))
(defun ast:g-lean (settings)
  ;; Legacy handedness describes the displayed material face.
  (* (ast:g-get 'lean settings (* pi (/ 40.0 180.0)))
     (ast:g-get 'handedness settings 1) (ast:g-get 'stitch-hand settings 1)))
(defun ast:g-axis (primitive station settings / tangent lean)
  (setq tangent (ast:g-tangent primitive station) lean (ast:g-lean settings))
  (ast:g-add (ast:g-mul tangent (cos lean)) (ast:g-mul (ast:g-left tangent) (sin lean))))
(defun ast:g-slit (primitive station settings)
  (list '(type . slit) (cons 'center (ast:g-point primitive station)) (cons 'axis (ast:g-axis primitive station settings)) (cons 'length (ast:g-get 'slit-length settings 1.5))))
(defun ast:g-step (primitive pitch)
  (if (= (cdr (assoc 'kind primitive)) 'line) pitch
    (* 2.0 (cdr (assoc 'radius primitive)) (ast:g-asin (/ pitch (* 2.0 (cdr (assoc 'radius primitive))))))))
(defun ast:g-profile-error (settings / pitch slit lean hand width diameter margin)
  (setq pitch (ast:g-get 'pitch settings 3.0) slit (ast:g-get 'slit-length settings 1.5)
        lean (ast:g-get 'lean settings (* pi (/ 40.0 180.0))) hand (ast:g-get 'handedness settings 1)
        diameter (ast:g-get 'diameter settings 0.5) width (ast:g-get 'thickness settings nil) margin (ast:g-get 'margin settings nil))
  (cond ((not (and (ast:g-finite pitch) (> pitch 0) (ast:g-finite slit) (> slit 0) (ast:g-finite lean) (member hand '(-1 1)) (ast:g-finite diameter) (> diameter 0))) "The pitch or hole dimensions are invalid. Check the pitch and tool settings.")
        ((not (member (ast:g-get 'stitch-hand settings 1) '(-1 1))) "Choose Obverse or Reverse for the stitch lean.")
        ((and width (not (and (ast:g-finite width) (>= width 0)))) "The slit width is invalid. Enter a width of zero or more in the tool settings.")
        ((and margin (not (and (ast:g-finite margin) (>= margin 0)))) "The material margin is invalid. Enter a distance of zero or more in the tool settings.")))
(defun ast:g-primitive-error (primitive / kind)
  (setq kind (ast:g-get 'kind primitive nil))
  (cond ((= kind 'line)
    (if (not (and (ast:g-pointp (ast:g-get 'a primitive nil)) (ast:g-pointp (ast:g-get 'b primitive nil)) (> (ast:g-length primitive) 1e-9))) "A guide segment has no usable length. Remove it or extend it."))
    ((= kind 'arc)
      (if (not (and (ast:g-pointp (ast:g-get 'center primitive nil)) (ast:g-finite (ast:g-get 'radius primitive nil)) (> (ast:g-get 'radius primitive 0) 0)
                    (ast:g-finite (ast:g-get 'start-angle primitive nil)) (ast:g-finite (ast:g-get 'sweep primitive nil))
                    (> (abs (ast:g-get 'sweep primitive 0)) 1e-12) (<= (abs (ast:g-get 'sweep primitive 0)) (+ (* 2.0 pi) 1e-10)))) "A curved guide segment is invalid or turns more than a full circle. Redraw that segment."))
    (T "This guide contains unsupported curves. Use straight lines or circular arcs.")))

(defun ast:g-point-segment-distance (point aa bb / delta factor)
  (setq delta (ast:g-sub bb aa) factor (ast:g-clamp (/ (ast:g-dot (ast:g-sub point aa) delta) (ast:g-dot delta delta)) 0.0 1.0))
  (ast:g-dist point (ast:g-add aa (ast:g-mul delta factor))))
(defun ast:g-segment-distance (aa bb cc dd / rr ss denominator uu vv)
  (setq rr (ast:g-sub bb aa) ss (ast:g-sub dd cc) denominator (ast:g-cross rr ss))
  (if (> (abs denominator) 1e-14)
    (setq uu (/ (ast:g-cross (ast:g-sub cc aa) ss) denominator) vv (/ (ast:g-cross (ast:g-sub cc aa) rr) denominator)))
  (if (and uu vv (>= uu 0) (<= uu 1) (>= vv 0) (<= vv 1)) 0.0
    (min (ast:g-point-segment-distance aa cc dd) (ast:g-point-segment-distance bb cc dd)
         (ast:g-point-segment-distance cc aa bb) (ast:g-point-segment-distance dd aa bb))))
(defun ast:g-ends (opening / vector center)
  (setq center (cdr (assoc 'center opening)) vector (ast:g-mul (cdr (assoc 'axis opening)) (/ (cdr (assoc 'length opening)) 2.0)))
  (list (ast:g-sub center vector) (ast:g-add center vector)))
(defun ast:g-clearance (first second settings / ends-a ends-b actual required width margin type-a type-b)
  (setq type-a (cdr (assoc 'type first)) type-b (cdr (assoc 'type second)) width (ast:g-get 'thickness settings 0.0) margin (ast:g-get 'margin settings 0.0))
  (if (null width) (setq width 0.0)) (if (null margin) (setq margin 0.0))
  (cond
    ((and (= type-a 'slit) (= type-b 'slit))
      (setq ends-a (ast:g-ends first) ends-b (ast:g-ends second) actual (ast:g-segment-distance (car ends-a) (cadr ends-a) (car ends-b) (cadr ends-b)) required (+ width margin)))
    ((and (= type-a 'round) (= type-b 'round))
      (setq actual (ast:g-dist (cdr (assoc 'center first)) (cdr (assoc 'center second))) required (+ (/ (+ (cdr (assoc 'diameter first)) (cdr (assoc 'diameter second))) 2.0) margin)))
    (T (if (= type-a 'round) (setq ends-a first first second second ends-a))
      (setq ends-a (ast:g-ends first) actual (ast:g-point-segment-distance (cdr (assoc 'center second)) (car ends-a) (cadr ends-a)) required (+ (/ width 2.0) (/ (cdr (assoc 'diameter second)) 2.0) margin))))
  ;; Finite slit capsules and round disks cannot touch. Actual is axis/centre
  ;; distance; required includes their widths/radii and the retained-material margin.
  (if (or (< actual (- required (ast:g-tol required))) (<= actual (+ (- required margin) (ast:g-tol required))) (<= actual 1e-9))
    "Two stitch holes touch or leave too little material between them. Spread the stitching farther apart or change the corner or curve."))
(defun ast:g-opening-box (opening width / first-point second-point radius low-x low-y high-x high-y ends)
  (if (= (ast:g-get 'type opening nil) 'slit)
    (progn (setq ends (ast:g-ends opening) first-point (car ends) second-point (cadr ends) radius (/ width 2.0)))
    (setq first-point (ast:g-get 'center opening nil) second-point first-point radius (/ (ast:g-get 'diameter opening 0.0) 2.0)))
  (setq low-x (- (min (car first-point) (car second-point)) radius)
        low-y (- (min (cadr first-point) (cadr second-point)) radius)
        high-x (+ (max (car first-point) (car second-point)) radius)
        high-y (+ (max (cadr first-point) (cadr second-point)) radius))
  (list low-x low-y high-x high-y (ast:g-tol (max (abs low-x) (abs low-y) (abs high-x) (abs high-y)))))
(defun ast:g-box-separated (aa bb margin / threshold)
  ;; Each capsule/disk is contained in its box. Separation on either axis greater
  ;; than the margin proves clearance; touching/overlapping boxes still use the
  ;; original exact footprint check. Coordinate tolerance only prevents skips.
  (setq threshold (+ (max margin 1e-9) (nth 4 aa) (nth 4 bb)))
  (or (> (- (car bb) (nth 2 aa)) threshold) (> (- (car aa) (nth 2 bb)) threshold)
      (> (- (cadr bb) (nth 3 aa)) threshold) (> (- (cadr aa) (nth 3 bb)) threshold)))
(defun ast:g-validate-openings (openings settings / tail rest error width margin opening boxes)
  (if (> (length openings) 2000) (setq error "This stitch line needs more than 2000 holes. Split the guide into shorter stitch lines."))
  (setq width (ast:g-get 'thickness settings 0.0) margin (ast:g-get 'margin settings 0.0))
  (if (null width) (setq width 0.0)) (if (null margin) (setq margin 0.0))
  (if (null error)
    (foreach opening openings (setq boxes (cons (cons opening (ast:g-opening-box opening width)) boxes))))
  (setq tail (reverse boxes))
  (while (and tail (null error))
    (setq rest (cdr tail))
    (while (and rest (null error))
      (if (not (ast:g-box-separated (cdar tail) (cdar rest) margin))
        (setq error (ast:g-clearance (caar tail) (caar rest) settings)))
      (setq rest (cdr rest)))
    (setq tail (cdr tail))) error)

;;; A sorted landmark reserves a nominal gap. No landmark is converted to a hole.
(defun ast:g-solve-primitive (primitive settings landmarks start finish / pitch step ordered marker station left right cursor fit openings intervals error reserved advances gaps advance gap next kind span opening-count free-length station-tol point)
  (setq pitch (ast:g-get 'pitch settings 3.0) step (ast:g-step primitive pitch) cursor start
        ordered (vl-sort landmarks '(lambda (aa bb) (< (cdr (assoc 'station aa)) (cdr (assoc 'station bb)))))
        openings (list (ast:g-slit primitive start settings)) opening-count 1
        station-tol (max (ast:g-length primitive) (abs start) (abs finish) (ast:g-get 'radius primitive 0.0)))
  ;; Derived stations include roundoff from world-coordinate intersections.
  (foreach point (if (= (ast:g-get 'kind primitive nil) 'line)
                   (list (ast:g-get 'a primitive nil) (ast:g-get 'b primitive nil))
                   (list (ast:g-get 'center primitive nil)))
    (setq station-tol (max station-tol (abs (car point)) (abs (cadr point)))))
  (setq station-tol (ast:g-tol station-tol))
  (foreach marker ordered
    (setq station (ast:g-get 'station marker nil))
    (if (not (ast:g-finite station)) (setq error "A landmark position is invalid. Remove that landmark and add it again.")
      (progn
        (setq left (- station (/ step 2.0)) right (+ station (/ step 2.0)))
        (if (or (< left (- cursor 1e-9)) (> right (+ finish 1e-9))) (setq error "A landmark is too close to an endpoint, another landmark or a junction for this pitch. Remove it and add it farther away.")
          (setq reserved (append reserved (list (list cursor left nil) (list left right T))) cursor right)))))
  (setq reserved (append reserved (list (list cursor finish nil))))
  (foreach span reserved
    (if (null error)
      (progn
        (setq cursor (car span) next (cadr span))
        ;; Coincident derived anchors can differ by roundoff after subtraction.
        ;; Compare their stations first; a genuinely short positive span must fail.
        (setq free-length (if (<= (abs (- next cursor)) station-tol) 0.0 (max 0.0 (- next cursor))))
        (if (caddr span)
          (setq fit (list '(ok . T) (cons 'gaps (list pitch)) (cons 'advances (list (if (= (cdr (assoc 'kind primitive)) 'arc) (/ step (cdr (assoc 'radius primitive))) step)))))
          (setq fit (ast:g-fit (if (= (cdr (assoc 'kind primitive)) 'arc) (/ free-length (cdr (assoc 'radius primitive))) free-length) pitch (ast:g-get 'radius primitive nil) 0 0 (ast:g-get 'corrections settings T))))
        (if (not (cdr (assoc 'ok fit))) (setq error (cdr (assoc 'error fit)))
          (progn
            (setq gaps (cdr (assoc 'gaps fit)) advances (cdr (assoc 'advances fit)))
            (while (and gaps (null error))
              (setq gap (car gaps) advance (car advances) station (+ cursor (if (= (cdr (assoc 'kind primitive)) 'arc) (* advance (cdr (assoc 'radius primitive))) advance))
                    kind (if (ast:g-near gap pitch) 'ordinary 'corrected)
                    intervals (cons (list (cons 'kind kind) (cons 'distance gap) (cons 'start-station cursor) (cons 'end-station station) (cons 'reserved (caddr span))) intervals)
                    openings (cons (ast:g-slit primitive station settings) openings) cursor station gaps (cdr gaps) advances (cdr advances) opening-count (1+ opening-count))
              ;; One temporary closing duplicate is removed by the route planner.
              (if (> opening-count 2001) (setq error "This stitch line needs more than 2000 holes. Split the guide into shorter stitch lines."))))))))
  (if error (ast:g-error error) (list '(ok . T) (cons 'openings (reverse openings)) (cons 'intervals (reverse intervals)))))

;;; Intersect supporting lines/circles analytically; never select a remote fallback.
(defun ast:g-intersections (aa bb / vector denominator projection constant discriminant root direction distance-along height base separation ra rb)
  (cond
    ((and (= (ast:g-get 'kind aa nil) 'line) (= (ast:g-get 'kind bb nil) 'line))
      (setq denominator (ast:g-cross (cdr (assoc 'tangent aa)) (cdr (assoc 'tangent bb))))
      (if (< (abs denominator) 1e-12)
        (list (cons 'coincident (< (abs (ast:g-cross (ast:g-sub (cdr (assoc 'point bb)) (cdr (assoc 'point aa))) (cdr (assoc 'tangent aa)))) 1e-8)) '(points))
        (list (cons 'points (list (ast:g-add (cdr (assoc 'point aa)) (ast:g-mul (cdr (assoc 'tangent aa)) (/ (ast:g-cross (ast:g-sub (cdr (assoc 'point bb)) (cdr (assoc 'point aa))) (cdr (assoc 'tangent bb))) denominator))))))))
    ((and (/= (ast:g-get 'kind aa nil) 'line) (= (ast:g-get 'kind bb nil) 'line)) (ast:g-intersections bb aa))
    ((= (ast:g-get 'kind aa nil) 'line)
      (setq vector (ast:g-sub (cdr (assoc 'point aa)) (cdr (assoc 'center bb)))
            projection (ast:g-dot vector (cdr (assoc 'tangent aa))) constant (- (ast:g-dot vector vector) (expt (cdr (assoc 'radius bb)) 2))
            discriminant (- (* projection projection) constant))
      (if (< discriminant (- (ast:g-tol (max (abs constant) (* projection projection))))) '((points))
        (progn (setq root (sqrt (max 0.0 discriminant)) base (ast:g-add (cdr (assoc 'point aa)) (ast:g-mul (cdr (assoc 'tangent aa)) (- projection))))
          (list (cons 'points (if (< root 1e-9) (list base) (list (ast:g-add base (ast:g-mul (cdr (assoc 'tangent aa)) root)) (ast:g-sub base (ast:g-mul (cdr (assoc 'tangent aa)) root)))))))))
    (T
      (setq vector (ast:g-sub (cdr (assoc 'center bb)) (cdr (assoc 'center aa))) separation (ast:g-norm vector) ra (cdr (assoc 'radius aa)) rb (cdr (assoc 'radius bb)))
      (cond ((< separation 1e-9) (list (cons 'coincident (< (abs (- ra rb)) 1e-9)) '(points)))
            ((or (> separation (+ ra rb 1e-9)) (< separation (- (abs (- ra rb)) 1e-9))) '((points)))
            (T (setq direction (ast:g-mul vector (/ 1.0 separation)) distance-along (/ (+ (* ra ra) (- (* rb rb)) (* separation separation)) (* 2.0 separation))
                     height (sqrt (max 0.0 (- (* ra ra) (* distance-along distance-along)))) base (ast:g-add (cdr (assoc 'center aa)) (ast:g-mul direction distance-along)))
              (list (cons 'points (if (< height 1e-9) (list base) (list (ast:g-add base (ast:g-mul (ast:g-left direction) height)) (ast:g-sub base (ast:g-mul (ast:g-left direction) height)))))))))))
(defun ast:g-locus (primitive station tip-sign settings / half lean sigma coefficient-a coefficient-b)
  (setq half (/ (ast:g-get 'slit-length settings 1.5) 2.0))
  (if (= (ast:g-get 'kind primitive nil) 'line)
    (list '(kind . line) (cons 'point (ast:g-add (ast:g-point primitive station) (ast:g-mul (ast:g-axis primitive station settings) (* tip-sign half)))) (cons 'tangent (ast:g-tangent primitive station)))
    (progn
      (setq lean (ast:g-lean settings) sigma (ast:g-sign (ast:g-get 'sweep primitive 0))
            coefficient-a (- (ast:g-get 'radius primitive 0) (* tip-sign half sigma (sin lean))) coefficient-b (* tip-sign half sigma (cos lean)))
      (list '(kind . circle) (cons 'center (ast:g-get 'center primitive nil)) (cons 'radius (sqrt (+ (* coefficient-a coefficient-a) (* coefficient-b coefficient-b))))
            (cons 'coefficient-a coefficient-a) (cons 'coefficient-b coefficient-b)))))
(defun ast:g-virtual-station (primitive reference locus joint / vector radial radial-zero angle)
  (if (= (ast:g-get 'kind primitive nil) 'line)
    (ast:g-dot (ast:g-sub joint (ast:g-get 'point locus nil)) (ast:g-get 'tangent locus nil))
    (progn
      (setq vector (ast:g-sub joint (ast:g-get 'center primitive nil))
            radial (ast:g-mul (ast:g-sub (ast:g-mul vector (ast:g-get 'coefficient-a locus 0)) (ast:g-mul (ast:g-left vector) (ast:g-get 'coefficient-b locus 0))) (/ 1.0 (expt (ast:g-get 'radius locus 0) 2)))
            radial-zero (ast:g-mul (ast:g-sub (ast:g-point primitive reference) (ast:g-get 'center primitive nil)) (/ 1.0 (ast:g-get 'radius primitive 0)))
            angle (atan (ast:g-cross radial-zero radial) (ast:g-dot radial-zero radial)))
      (if (ast:g-near (abs angle) pi) nil (* (ast:g-sign (ast:g-get 'sweep primitive 0)) (ast:g-get 'radius primitive 0) angle)))))
(defun ast:g-corner-step (primitive pitch lower upper corrections / nominal low high maximum)
  (setq nominal (ast:g-step primitive pitch)
        maximum (if (= (ast:g-get 'kind primitive nil) 'arc)
          (min (* 1.1 pitch) (* 2.0 (ast:g-get 'radius primitive 0.0))) (* 1.1 pitch))
        low (max lower (if corrections (ast:g-step primitive (* 0.9 pitch)) nominal))
        high (min upper (if corrections (ast:g-step primitive maximum) nominal)))
  (if (<= low (+ high (ast:g-tol (max (abs low) (abs high)))))
    (ast:g-clamp nominal low high)))

(defun ast:g-corner-adjustment (real virtual nominal / distance)
  (setq distance (ast:g-dist (ast:g-get 'center real nil) (ast:g-get 'center virtual nil)))
  (if (> (abs (- distance nominal)) 1e-8)
    (list (cons 'center (ast:g-get 'center real nil))
      (cons 'virtual-center (ast:g-get 'center virtual nil))
      (cons 'nominal nominal) (cons 'distance distance))))

(defun ast:g-corner (incoming outgoing settings / vertex in-length out-length li lo intersection points first second joint ci co di dout pi-in pi-out virtual-in virtual-out before after hole error adjustments item)
  (setq in-length (ast:g-length incoming) out-length (ast:g-length outgoing) vertex (ast:g-point incoming in-length)
        li (ast:g-locus incoming in-length -1.0 settings) lo (ast:g-locus outgoing 0.0 1.0 settings)
        intersection (ast:g-intersections li lo) points (cdr (assoc 'points intersection)))
  ;; Selected slit-tip loci must have an isolated intersection. Coincident,
  ;; parallel and disjoint loci cannot choose a hole; tied nearest roots also fail.
  (cond
    ((null points) (ast:g-error "These stitch directions do not define one corner hole. Change the corner angle or curve shape."))
    (T
      (setq first (car points) second (cadr points))
      (if (and second (ast:g-near (expt (ast:g-dist first vertex) 2) (expt (ast:g-dist second vertex) 2))) (setq error "Two equally close corner-hole positions are possible. Adjust the corner angle or curve shape.")
        (setq joint (if (and second (< (ast:g-dist second vertex) (ast:g-dist first vertex))) second first)))
      (if (null error)
        (progn
          (setq ci (ast:g-virtual-station incoming in-length li joint) co (ast:g-virtual-station outgoing 0.0 lo joint)
                pi-in (ast:g-get 'incoming-pitch settings (ast:g-get 'pitch settings 3.0))
                pi-out (ast:g-get 'outgoing-pitch settings (ast:g-get 'pitch settings 3.0)))
          (if (and ci co)
            (setq di (ast:g-corner-step incoming pi-in ci (+ in-length ci)
                    (ast:g-get 'incoming-corrections settings (ast:g-get 'corrections settings T)))
                  dout (ast:g-corner-step outgoing pi-out (- co) (- out-length co)
                    (ast:g-get 'outgoing-corrections settings (ast:g-get 'corrections settings T)))))
          ;; Antipodal arc stations are ambiguous. Both real neighbours must fit
          ;; the finite arms; never substitute a remote root or another revolution.
          (cond ((or (null ci) (null co)) (setq error "This curved corner has no unique nearby stitch position. Adjust the curve shape."))
                ((or (null di) (null dout))
                  (setq error
                    (if (or (< (+ in-length ci) (ast:g-step incoming (* pi-in
                              (if (ast:g-get 'incoming-corrections settings (ast:g-get 'corrections settings T)) 0.9 1.0))))
                            (< (- out-length co) (ast:g-step outgoing (* pi-out
                              (if (ast:g-get 'outgoing-corrections settings (ast:g-get 'corrections settings T)) 0.9 1.0)))))
                      "A guide is too short for its corner stitch, even with the spacing allowance. Lengthen it or change the pitch."
                      "The corner puts a stitch past the junction, even with the spacing allowance. Increase the pitch or change the corner angle or curve.")))
                (T
                  (setq virtual-in (ast:g-slit incoming (+ in-length ci) settings) virtual-out (ast:g-slit outgoing co settings))
                  ;; Parallel virtual slit axes make the selected-tip contact degenerate.
                  (if (< (abs (ast:g-cross (ast:g-get 'axis virtual-in nil) (ast:g-get 'axis virtual-out nil))) 1e-9)
                    (setq error "The slit directions at this corner are parallel. Change the corner angle or curve shape.")
                    (progn
                      (setq before (ast:g-slit incoming (ast:g-clamp (+ in-length ci (- di)) 0.0 in-length) settings)
                            after (ast:g-slit outgoing (ast:g-clamp (+ co dout) 0.0 out-length) settings)
                            hole (list '(type . round) (cons 'center joint) (cons 'diameter (ast:g-get 'diameter settings 0.5)))
                            error (ast:g-validate-openings (list before hole after) settings))
                      (foreach item (list (ast:g-corner-adjustment before virtual-in pi-in)
                                          (ast:g-corner-adjustment after virtual-out pi-out))
                        (if item (setq adjustments (append adjustments (list item)))))))))))
      (if error (ast:g-error error)
        (list '(ok . T) (cons 'incoming-station (ast:g-clamp (+ in-length ci (- di)) 0.0 in-length))
          (cons 'outgoing-station (ast:g-clamp (+ co dout) 0.0 out-length))
          (cons 'opening hole) (cons 'virtual-slits (list virtual-in virtual-out))
          (cons 'corner-adjustments adjustments))))))

(defun ast:g-mergeable (aa bb / kind)
  (setq kind (ast:g-get 'kind aa nil))
  (and (= kind (ast:g-get 'kind bb nil))
       (< (ast:g-dist (ast:g-point aa (ast:g-length aa)) (ast:g-point bb 0.0)) 1e-8)
       (> (ast:g-dot (ast:g-tangent aa (ast:g-length aa)) (ast:g-tangent bb 0.0)) 0.0)
       (< (abs (ast:g-cross (ast:g-tangent aa (ast:g-length aa)) (ast:g-tangent bb 0.0))) 1e-10)
       (or (= kind 'line) (and (< (ast:g-dist (ast:g-get 'center aa nil) (ast:g-get 'center bb nil)) 1e-8)
                               (< (abs (- (ast:g-get 'radius aa 0) (ast:g-get 'radius bb 0))) 1e-8)
                               (<= (abs (+ (ast:g-get 'sweep aa 0) (ast:g-get 'sweep bb 0))) (+ (* 2.0 pi) 1e-10))))))
(defun ast:g-merge (aa bb)
  (if (= (ast:g-get 'kind aa nil) 'line)
    (subst (cons 'b (ast:g-get 'b bb nil)) (assoc 'b aa) aa)
    (subst (cons 'sweep (+ (ast:g-get 'sweep aa 0) (ast:g-get 'sweep bb 0))) (assoc 'sweep aa) aa)))
(defun ast:g-reverse-primitive (primitive)
  (if (= (ast:g-get 'kind primitive nil) 'line)
    (list '(kind . line) (cons 'a (ast:g-get 'b primitive nil)) (cons 'b (ast:g-get 'a primitive nil)))
    (list '(kind . arc) (cons 'center (ast:g-get 'center primitive nil)) (cons 'radius (ast:g-get 'radius primitive 0))
          (cons 'start-angle (+ (ast:g-get 'start-angle primitive 0) (ast:g-get 'sweep primitive 0))) (cons 'sweep (- (ast:g-get 'sweep primitive 0))))))
(defun ast:g-normalize (primitives landmarks reverse-travel / error marker index station offset total distances absolute normalized primitive remapped found running)
  (setq total 0.0)
  (foreach primitive primitives (setq distances (append distances (list total)) total (+ total (ast:g-length primitive))))
  (foreach marker landmarks
    (setq index (ast:g-get 'primitive marker 0) station (ast:g-get 'station marker nil))
    (if (not (and (numberp index) (= index (fix index)) (>= index 0) (< index (length primitives)) (ast:g-finite station)))
      (setq error "A landmark no longer has a valid position on this line. Remove it and add it again.")
      (if (or (< station 0.0) (> station (ast:g-length (nth index primitives)))) (setq error "A landmark is past the end of its guide segment. Extend that segment, or remove and add the landmark again.")
        (progn (setq offset (+ (nth index distances) station)) (setq absolute (cons (if reverse-travel (- total offset) offset) absolute))))))
  (if reverse-travel (setq primitives (mapcar 'ast:g-reverse-primitive (reverse primitives))))
  (foreach primitive primitives
    (if (and normalized (ast:g-mergeable (car normalized) primitive)) (setq normalized (cons (ast:g-merge (car normalized) primitive) (cdr normalized))) (setq normalized (cons primitive normalized))))
  (setq normalized (reverse normalized))
  (foreach station absolute
    (setq index 0 running 0.0 found nil)
    (foreach primitive normalized
      (if (and (null found) (<= station (+ running (ast:g-length primitive) 1e-9)))
        (setq remapped (cons (list (cons 'primitive index) (cons 'station (- station running))) remapped) found T))
      (setq running (+ running (ast:g-length primitive)) index (1+ index))))
  (if error (ast:g-error error) (list '(ok . T) (cons 'primitives normalized) (cons 'landmarks (reverse remapped)))))

(defun ast:g-support (primitive)
  (if (= (ast:g-get 'kind primitive nil) 'line)
    (list '(kind . line) (cons 'point (ast:g-point primitive 0.0)) (cons 'tangent (ast:g-tangent primitive 0.0)))
    (list '(kind . circle) (cons 'center (ast:g-get 'center primitive nil)) (cons 'radius (ast:g-get 'radius primitive 0)))))
(defun ast:g-point-on (primitive point / radial angle sweep)
  (if (= (ast:g-get 'kind primitive nil) 'line)
    (and (< (ast:g-point-segment-distance point (ast:g-point primitive 0.0) (ast:g-point primitive (ast:g-length primitive))) 1e-8))
    (progn
      (setq radial (ast:g-sub point (ast:g-get 'center primitive nil)) angle (- (atan (cadr radial) (car radial)) (ast:g-get 'start-angle primitive 0)) sweep (ast:g-get 'sweep primitive 0))
      (setq angle (* (ast:g-sign sweep) angle))
      (while (< angle -1e-9) (setq angle (+ angle (* 2.0 pi))))
      (while (> angle (+ (* 2.0 pi) 1e-9)) (setq angle (- angle (* 2.0 pi))))
      (and (< (abs (- (ast:g-norm radial) (ast:g-get 'radius primitive 0))) 1e-8) (<= angle (+ (abs sweep) 1e-9))))))
(defun ast:g-route-crossing (primitives closed / ii jj aa bb hit point allowed crossing sample)
  (setq ii 0)
  (foreach aa primitives
    (setq jj (1+ ii))
    (while (< jj (length primitives))
      (setq bb (nth jj primitives) hit (ast:g-intersections (ast:g-support aa) (ast:g-support bb)) allowed nil)
      (if (= jj (1+ ii)) (setq allowed (cons (ast:g-point aa (ast:g-length aa)) allowed)))
      (if (and closed (= ii 0) (= jj (1- (length primitives)))) (setq allowed (cons (ast:g-point aa 0.0) allowed)))
      (foreach point (ast:g-get 'points hit nil)
        (if (and (ast:g-point-on aa point) (ast:g-point-on bb point) (not (vl-some '(lambda (sample) (< (ast:g-dist sample point) 1e-8)) allowed))) (setq crossing T)))
      (if (ast:g-get 'coincident hit nil)
        (progn
          (foreach point (list (ast:g-point aa 0.0) (ast:g-point aa (/ (ast:g-length aa) 2.0)) (ast:g-point aa (ast:g-length aa)))
            (if (and (ast:g-point-on bb point) (not (vl-some '(lambda (sample) (< (ast:g-dist sample point) 1e-8)) allowed))) (setq crossing T)))
          (foreach point (list (ast:g-point bb 0.0) (ast:g-point bb (/ (ast:g-length bb) 2.0)) (ast:g-point bb (ast:g-length bb)))
            (if (and (ast:g-point-on aa point) (not (vl-some '(lambda (sample) (< (ast:g-dist sample point) 1e-8)) allowed))) (setq crossing T)))))
      (setq jj (1+ jj))) (setq ii (1+ ii)))
  (if crossing "This guide crosses or overlaps itself. Split crossings into separate lines and connect them; remove overlaps."))
(defun ast:g-same-opening (aa bb)
  (and (= (ast:g-get 'type aa nil) (ast:g-get 'type bb nil)) (< (ast:g-dist (ast:g-get 'center aa nil) (ast:g-get 'center bb nil)) 1e-8)
    (if (= (ast:g-get 'type aa nil) 'slit)
      (and (< (abs (ast:g-cross (ast:g-get 'axis aa nil) (ast:g-get 'axis bb nil))) 1e-9) (ast:g-near (ast:g-get 'length aa 0) (ast:g-get 'length bb 0)))
      (ast:g-near (ast:g-get 'diameter aa 0) (ast:g-get 'diameter bb 0)))))
(defun ast:g-junction-interval (from-point to-point index)
  (list '(kind . junction) (cons 'primitive index) (cons 'from from-point) (cons 'to to-point) (cons 'distance (ast:g-dist from-point to-point))))

(defun ast:g-trim-primitive (primitive start finish)
  (if (= (ast:g-get 'kind primitive nil) 'line)
    (list '(kind . line) (cons 'a (ast:g-point primitive start)) (cons 'b (ast:g-point primitive finish)))
    (list '(kind . arc) (cons 'center (ast:g-get 'center primitive nil)) (cons 'radius (ast:g-get 'radius primitive 0))
          (cons 'start-angle (+ (ast:g-get 'start-angle primitive 0) (* (ast:g-sign (ast:g-get 'sweep primitive 0)) (/ start (ast:g-get 'radius primitive 0)))))
          (cons 'sweep (* (ast:g-sign (ast:g-get 'sweep primitive 0)) (/ (- finish start) (ast:g-get 'radius primitive 0)))))))
(defun ast:g-range (primitives landmarks settings closed / start finish phase total error remapped marker station index offsets absolute primitive cursor low high selected cycles found)
  (setq total 0.0)
  (foreach primitive primitives
    (setq offsets (append offsets (list total)) total (+ total (ast:g-length primitive))))
  (setq start (ast:g-get 'start settings 0.0) finish (ast:g-get 'end settings total) phase (ast:g-get 'phase settings 0.0))
  (if closed
    (if (or (assoc 'start settings) (assoc 'end settings)) (setq error "A closed loop needs one starting point, not separate start and end limits. Use Set start on the loop.")
      (if (not (and (ast:g-finite phase) (>= phase 0.0) (<= phase total))) (setq error "The saved loop start is no longer on the guide. Use Set start to choose it again.")
        (setq start phase finish (+ phase total))))
    (if (not (and (ast:g-finite start) (ast:g-finite finish) (>= start 0.0) (<= finish total) (> finish start)))
      (setq error "The start and end must lie on the guide, with some line between them. Pick them again.")))
  (foreach marker landmarks
    (setq index (ast:g-get 'primitive marker 0) station (ast:g-get 'station marker nil))
    (if (not (and (numberp index) (= index (fix index)) (>= index 0) (< index (length primitives)) (ast:g-finite station)))
      (setq error "A landmark no longer has a valid position on this line. Remove it and add it again.")
      (if (or (< station 0.0) (> station (ast:g-length (nth index primitives)))) (setq error "A landmark is past the end of its guide segment. Extend that segment, or remove and add the landmark again.")
        (progn
          (setq station (+ (nth index offsets) station))
          (if (and closed (< station start)) (setq station (+ station total)))
          (if (or (< station start) (> station finish)) (setq error "A landmark lies outside the chosen start and end. Extend the stitching to include it, or remove the landmark.")
            (setq absolute (cons (- station start) absolute)))))))
  (if (null error)
    (progn
      ;; A closed phase cuts the owning primitive, then visits the remainder once.
      (setq cursor 0.0 cycles (if closed 2 1))
      (repeat cycles
        (foreach primitive primitives
          (setq low (max start cursor) high (min finish (+ cursor (ast:g-length primitive))))
          (if (> (- high low) 1e-9)
            (setq selected (cons (ast:g-trim-primitive primitive (- low cursor) (- high cursor)) selected)))
          (setq cursor (+ cursor (ast:g-length primitive)))))
      (setq selected (reverse selected))
      (foreach station (reverse absolute)
        (setq index 0 cursor 0.0 found nil)
        (foreach primitive selected
          (if (and (null found) (<= station (+ cursor (ast:g-length primitive) 1e-9)))
            (setq remapped (cons (list (cons 'primitive index) (cons 'station (- station cursor))) remapped) found T))
          (setq cursor (+ cursor (ast:g-length primitive)) index (1+ index))))))
  (if error (ast:g-error error) (list '(ok . T) (cons 'primitives selected) (cons 'landmarks (reverse remapped)))))

(defun ast:g-solve (route settings landmarks / primitives primitive marker error normalized closed count idx incoming outgoing result joins corner openings intervals local-openings local-intervals selected join start finish warnings previous range joint-center after-center adjusted virtual-slits corner-adjustments)
  (setq primitives (ast:g-get 'primitives route nil) closed (ast:g-get 'closed route nil) error (ast:g-profile-error settings))
  (if (null primitives) (setq error "No usable stitch line was found. Select a line or curve."))
  (foreach primitive primitives (if (null error) (setq error (ast:g-primitive-error primitive))))
  (if (null error)
    (progn
      (foreach primitive primitives
        (if (and previous (> (ast:g-dist (ast:g-point previous (ast:g-length previous)) (ast:g-point primitive 0.0)) 1e-8)) (setq error "The guide has a break between segments. Join their endpoints or stitch them as separate lines."))
        (setq previous primitive))
      (if (and closed (> (ast:g-dist (ast:g-point (car primitives) 0.0) (ast:g-point previous (ast:g-length previous))) 1e-8)) (setq error "The closed guide has a gap at its join. Close that gap before generating stitches."))))
  (if (null error)
    (progn
      (setq range (ast:g-range primitives landmarks settings closed))
      (if (not (ast:g-get 'ok range nil)) (setq error (ast:g-get 'error range nil))
        (setq primitives (ast:g-get 'primitives range nil) landmarks (ast:g-get 'landmarks range nil)))))
  (if (null error)
    (progn
      (setq normalized (ast:g-normalize primitives landmarks (ast:g-get 'reverse settings nil)))
      (if (not (ast:g-get 'ok normalized nil)) (setq error (ast:g-get 'error normalized nil))
        (setq primitives (ast:g-get 'primitives normalized nil) landmarks (ast:g-get 'landmarks normalized nil)))))
  (foreach primitive primitives
    (if (and (null error) (= (ast:g-get 'kind primitive nil) 'arc) (> (ast:g-get 'pitch settings 3.0) (* 2.0 (ast:g-get 'radius primitive 0)))) (setq error "The pitch is too large for this curve. Reduce the pitch or increase the curve radius.")))
  (if (null error) (setq error (ast:g-route-crossing primitives closed)))
  (if (null error)
    (progn
      (setq count (length primitives) idx 0)
      (repeat (if closed count (1- count))
        (setq incoming (nth idx primitives) outgoing (nth (rem (1+ idx) count) primitives))
        (if (and (> (ast:g-dot (ast:g-tangent incoming (ast:g-length incoming)) (ast:g-tangent outgoing 0.0)) 0.0)
                 (< (abs (ast:g-cross (ast:g-tangent incoming (ast:g-length incoming)) (ast:g-tangent outgoing 0.0))) 1e-10))
          (setq join (list '(kind . smooth) (cons 'incoming-station (ast:g-length incoming)) '(outgoing-station . 0.0)))
          (progn (setq corner (ast:g-corner incoming outgoing settings))
            (if (not (ast:g-get 'ok corner nil)) (setq error (ast:g-get 'error corner nil))
              (setq join (cons '(kind . sharp) corner)
                    virtual-slits (append virtual-slits (ast:g-get 'virtual-slits corner nil))
                    corner-adjustments (append corner-adjustments (ast:g-get 'corner-adjustments corner nil))))))
        (setq joins (append joins (list join)) idx (1+ idx)))
      (setq idx 0)
      (foreach primitive primitives
        (setq start (if (> idx 0) (ast:g-get 'outgoing-station (nth (1- idx) joins) 0.0) (if closed (ast:g-get 'outgoing-station (nth (1- count) joins) 0.0) 0.0))
              finish (if (< idx (length joins)) (ast:g-get 'incoming-station (nth idx joins) (ast:g-length primitive)) (ast:g-length primitive)))
        (if (> start (+ finish 1e-8)) (setq error "There is not enough room for the stitches between these corners. Move the corners apart or lengthen the section."))
        (if (null error)
          (progn
            (setq selected nil)
            (foreach marker landmarks (if (= (ast:g-get 'primitive marker 0) idx) (setq selected (cons marker selected))))
            (setq result (ast:g-solve-primitive primitive settings selected start finish))
            (if (not (ast:g-get 'ok result nil)) (setq error (ast:g-get 'error result "Stitches could not be fitted to this section."))
              (progn
                (setq local-openings (ast:g-get 'openings result nil) local-intervals (ast:g-get 'intervals result nil))
                (if (and openings local-openings (ast:g-same-opening (last openings) (car local-openings))) (setq local-openings (cdr local-openings)))
                (setq openings (append openings local-openings) intervals (append intervals (mapcar '(lambda (item) (cons (cons 'primitive idx) item)) local-intervals)))
                (if (> (length openings) 2001) (setq error "This stitch line needs more than 2000 holes. Split the guide into shorter stitch lines."))
                (if (and (< idx (length joins)) (= (ast:g-get 'kind (nth idx joins) nil) 'sharp))
                  (progn
                    (setq joint-center (ast:g-get 'center (ast:g-get 'opening (nth idx joins) nil) nil)
                          after-center (ast:g-point (nth (rem (1+ idx) count) primitives) (ast:g-get 'outgoing-station (nth idx joins) 0.0))
                          openings (append openings (list (ast:g-get 'opening (nth idx joins) nil)))
                          intervals (append intervals (list (ast:g-junction-interval (ast:g-point primitive finish) joint-center idx)
                                                            (ast:g-junction-interval joint-center after-center (rem (1+ idx) count)))))))))))
        (setq idx (1+ idx)))
      (if (and (null error) closed (> (length openings) 1) (ast:g-same-opening (car openings) (last openings))) (setq openings (reverse (cdr (reverse openings)))))
      (if (null error) (setq error (ast:g-validate-openings openings settings)))))
  (if error (ast:g-error error)
    (progn
      (setq warnings (list "The distance from stitch holes to the material edge has not been checked."))
      (if (or (null (ast:g-get 'thickness settings nil)) (null (ast:g-get 'margin settings nil))) (setq warnings (cons "Slit width and the material needed between holes have not been calibrated." warnings)))
      (if (vl-some '(lambda (item) (= (ast:g-get 'kind item nil) 'arc)) primitives) (setq warnings (cons "Place holes individually on curves; a multi-tooth chisel may not follow the curve." warnings)))
      (setq adjusted (or corner-adjustments (vl-some '(lambda (item) (= (ast:g-get 'kind item nil) 'corrected)) intervals)))
      (if adjusted (setq warnings (cons "Use individual placement where spacing is adjusted; a fixed-pitch chisel will not match it." warnings)))
      (list '(ok . T) (cons 'status (if adjusted 'adjusted 'exact)) (cons 'openings openings) (cons 'intervals intervals)
        (cons 'virtual-slits virtual-slits) (cons 'corner-adjustments corner-adjustments)
        (cons 'warnings warnings) (cons 'primitives primitives) (cons 'landmarks landmarks)))))
(princ)
