;;; Separate pattern pieces share one solved layout; junction ownership stays in the CAD adapter.
(defun ast:match-record (entity / ast:*cad-key*)
  (setq ast:*cad-key* "AUTOSTITCH_MATCH_V1") (ast:cad-record entity))
(defun ast:match-write-record (entity record / ast:*cad-key*)
  (setq ast:*cad-key* "AUTOSTITCH_MATCH_V1")
  (ast:cad-write-record entity
    (ast:cad-put 'identity (cdr (assoc 5 (entget entity)))
      (vl-remove-if '(lambda (item) (eq (car item) 'link)) record)) (ast:cad-get 'link record)))
(defun ast:match-remove-record (entity / dictionary record)
  (if (and entity (entget entity) (setq dictionary (cdr (assoc 360 (entget entity)))))
    (if (setq record (dictsearch dictionary "AUTOSTITCH_MATCH_V1"))
      (ast:cad-require (dictremove dictionary "AUTOSTITCH_MATCH_V1") "Could not remove the matched-guide link."))))
(defun ast:match-owner (state)
  (vl-some '(lambda (member) (if (and member (entget member)) member)) (ast:cad-get 'members state)))
(defun ast:match-info-inner (entity / state guide owner record primary members peer saved valid copied face error role missing)
  (setq state (ast:cad-read-base entity) guide (ast:cad-get 'guide state) owner (ast:match-owner state)
        record (ast:match-record guide))
  (if (null record) (setq record (ast:match-record owner)))
  (setq face (ast:g-get 'handedness (ast:cad-get 'settings state) 1))
  (if (null record) (list '(ok . T) (cons 'owner owner) (cons 'face face))
    (progn
      (setq primary (ast:cad-get 'primary record) members (ast:cad-get 'members record)
            copied (and (eq (type (ast:cad-get 'identity record)) 'STR)
              (not (equal (ast:cad-get 'identity record) (cdr (assoc 5 (entget guide))))))
            valid (and (equal 1 (ast:cad-get 'schema record)) (member owner members) primary (entget primary)))
      (foreach peer members
        (if (and peer (entget peer))
          (progn
            (setq saved (ast:match-record peer))
            (if (not (and (equal 1 (ast:cad-get 'schema saved)) (equal primary (ast:cad-get 'primary saved))
                          (equal members (ast:cad-get 'members saved)))) (setq valid nil)))
          (setq valid nil missing T)))
      ;; A partial native COPY must never acquire or regenerate the original family.
      (if (and copied (not valid)) (list '(ok . T) (cons 'owner owner) (cons 'face face))
        (progn
          (setq role (if (equal owner primary) 'source 'copy))
          (if (not valid) (setq error (if (and (eq role 'source) missing)
            "A matching copy was deleted. Use Remove missing to repair the matching set."
            "A matched guide was deleted or its link is incomplete. Unlink the affected copy, then match it again.")))
          (if (eq role 'copy) (setq face (ast:g-get 'face record face)))
          (list '(ok . T) '(active . T) (cons 'role role) (cons 'owner owner)
            (cons 'source primary) (cons 'targets (vl-remove primary members)) (cons 'members members)
            (cons 'face face) (cons 'record record) (cons 'repairable (and (eq role 'source) missing)) (cons 'error error)))))))
(defun ast:match-info (entity) (ast:cad-catch 'ast:match-info-inner (list entity)))
(defun ast:match-edit-error (entity / info)
  (setq info (ast:match-info entity))
  (cond ((ast:cad-get 'error info) (ast:cad-get 'error info))
        ((eq (ast:cad-get 'role info) 'copy) "This guide uses its source's stitch settings. Select the source to edit them, or unlink this copy.")))
(defun ast:match-topology-error (entity / info)
  (setq info (ast:match-info entity))
  (if (ast:cad-get 'active info) "Unlink matching copies before connecting, disconnecting or detaching these guides."
    (ast:cad-get 'error info)))

(defun ast:match-states (owner selected settings landmarks / state)
  (setq state (ast:cad-read-base owner))
  (ast:cad-require (not (ast:cad-get 'missing-members state))
    "A source guide was deleted. Unlink its matching copies, then select the source and use Remove missing lines.")
  (ast:cad-set-states (ast:cad-get 'members state) selected settings landmarks))
(defun ast:match-raw-states (owner / state)
  (setq state (ast:cad-read-base owner))
  (ast:cad-require (not (ast:cad-get 'missing-members state))
    "A guide in this copy was deleted. Unlink the copy, then use Remove missing lines.")
  (mapcar 'ast:cad-read-base (ast:cad-get 'members state)))
(defun ast:match-ordered (states anchor / chosen)
  (setq chosen (vl-some '(lambda (state) (if (equal anchor (ast:cad-get 'guide state)) state)) states))
  (ast:cad-require chosen "The matching start guide was deleted. Unlink this copy, then match it again.")
  (cons chosen (vl-remove chosen states)))
(defun ast:match-connections (states / result)
  (setq result (ast:g-resolve-connections (ast:cad-set-paths states) (ast:cad-get 'connections (car states))))
  (ast:cad-require (ast:cad-get 'ok result) (ast:cad-get 'error result))
  (ast:cad-get 'connections result))
(defun ast:match-total (route) (apply '+ (mapcar 'ast:g-length (ast:cad-get 'primitives route))))
(defun ast:match-global (route attachment / index total primitive)
  (setq index 0 total (ast:cad-get 'station attachment))
  (foreach primitive (ast:cad-get 'primitives route)
    (if (< index (ast:cad-get 'primitive attachment)) (setq total (+ total (ast:g-length primitive))))
    (setq index (1+ index))) total)
(defun ast:match-attachment (route station / index primitives)
  (setq index 0 primitives (ast:cad-get 'primitives route))
  (while (and (cdr primitives) (> station (+ 1e-8 (ast:g-length (car primitives)))))
    (setq station (- station (ast:g-length (car primitives))) primitives (cdr primitives) index (1+ index)))
  (ast:cad-require (and (>= station -1e-7) (<= station (+ (ast:g-length (car primitives)) 1e-7)))
    "A matching landmark or endpoint falls outside its guide. Check the matching starts.")
  (list (cons 'primitive index) (cons 'station (ast:g-clamp station 0.0 (ast:g-length (car primitives))))))
(defun ast:match-station (station pair route / value total)
  (setq value (+ (ast:g-get 'phase pair 0.0) (* (if (ast:cad-get 'reversed pair) -1.0 1.0) station))
        total (ast:match-total route))
  (if (ast:cad-get 'closed route) (setq value (rem (+ (rem value total) total) total))) value)
(defun ast:match-settings (settings source-route target-route pair parity / result start finish phase anchor)
  (setq result (vl-remove-if '(lambda (item) (member (car item) '(start end phase start-anchor end-anchor phase-anchor reverse handedness))) settings)
        result (ast:cad-put 'handedness (* parity (ast:g-get 'handedness settings 1))
          (ast:cad-put 'reverse (not (eq (not (ast:cad-get 'reverse settings)) (not (ast:cad-get 'reversed pair)))) result)))
  (if (ast:cad-get 'closed source-route)
    (progn
      (setq phase (ast:match-station (ast:g-get 'phase settings 0.0) pair target-route)
            anchor (ast:cad-put 'source-route target-route (ast:match-attachment target-route phase))
            result (ast:cad-put 'phase phase (ast:cad-put 'phase-anchor anchor result))))
    (progn
      (setq start (ast:match-station (ast:g-get 'start settings 0.0) pair target-route)
            finish (ast:match-station (ast:g-get 'end settings (ast:match-total source-route)) pair target-route)
            result (ast:cad-put 'start (min start finish) (ast:cad-put 'end (max start finish) result))
            result (ast:cad-put 'start-anchor (ast:cad-put 'source-route target-route (ast:match-attachment target-route (min start finish))) result)
            result (ast:cad-put 'end-anchor (ast:cad-put 'source-route target-route (ast:match-attachment target-route (max start finish))) result))))
  result)
(defun ast:match-landmarks (landmarks source-route target-route pair)
  (mapcar '(lambda (landmark) (ast:match-attachment target-route
    (ast:match-station (ast:match-global source-route landmark) pair target-route))) landmarks))
(defun ast:match-path-set (node states / result incidence guide)
  (foreach incidence (ast:cad-get 'incidences node)
    (setq guide (ast:cad-get 'guide (nth (ast:cad-get 'path incidence) states)))
    (if (not (member guide result)) (setq result (cons guide result)))) result)
(defun ast:match-topology (source-states source-connections target-states target-connections guide-pairs transform / node mapped expected match)
  (ast:cad-require (= (length source-connections) (length target-connections))
    "These stitch lines have different junction connections. Connect the same guide intersections on both pieces first.")
  (foreach node source-connections
    (setq mapped (ast:m-point (ast:cad-get 'point node) transform)
          expected (mapcar '(lambda (guide) (cdr (assoc guide guide-pairs))) (ast:match-path-set node source-states))
          match (vl-some '(lambda (candidate)
            (if (and (< (ast:g-dist mapped (ast:cad-get 'point candidate)) 1e-7)
              (equal (length expected) (length (ast:match-path-set candidate target-states)))
              (vl-every '(lambda (guide) (member guide (ast:match-path-set candidate target-states))) expected)) candidate)) target-connections))
    (ast:cad-require match "The junctions do not correspond under this guide's placement. Check the matching starts and connections.")))

(defun ast:match-target-plan (source-states source-connections source-anchor registration-phase target record check-landmarks restore / target-states source-ordered target-ordered mapping alternative transform parity pairs pair source-state target-state source-route target-route settings landmarks original item mapped-states guide-pairs connections source-routes target-routes source-phase target-phase reversed)
  (if (assoc 'source-index record)
    (setq source-anchor (ast:cad-get 'guide (nth (ast:cad-get 'source-index record) source-states))))
  (setq target-states (ast:match-raw-states target)
        source-ordered (ast:match-ordered source-states source-anchor)
        target-ordered (ast:match-ordered target-states (ast:cad-get 'link record))
        parity (* (ast:g-get 'handedness (ast:cad-get 'settings (car source-ordered)) 1) (ast:g-get 'face record 1))
        source-routes (mapcar '(lambda (state) (ast:cad-get 'route state)) source-ordered)
        target-routes (mapcar '(lambda (state) (ast:cad-get 'route state)) target-ordered)
        source-phase (if (ast:cad-get 'closed (car source-routes))
          (if (assoc 'source-phase record) (ast:cad-get 'source-phase record) registration-phase))
        target-phase (if (ast:cad-get 'closed (car target-routes)) (ast:g-get 'target-phase record 0.0))
        reversed (ast:cad-get 'target-reversed record))
  (if (eq reversed 'auto)
    (progn
      (setq mapping (ast:m-map-routes source-routes target-routes parity nil source-phase target-phase)
            alternative (ast:m-map-routes source-routes target-routes parity T source-phase target-phase))
      (ast:cad-require (not (and (ast:cad-get 'ok mapping) (ast:cad-get 'ok alternative)))
        "The matching start permits two orientations. Choose another start point.")
      (if (ast:cad-get 'ok alternative) (setq mapping alternative reversed T) (setq reversed nil))
      (setq record (ast:cad-put 'target-reversed reversed record)))
    (setq mapping (ast:m-map-routes source-routes target-routes parity reversed source-phase target-phase)))
  (ast:cad-require (ast:cad-get 'ok mapping) (ast:cad-get 'error mapping))
  (setq transform (ast:cad-get 'transform mapping) pairs (ast:cad-get 'pairs mapping))
  (foreach pair pairs
    (setq source-state (nth (ast:cad-get 'source-index pair) source-ordered)
          target-state (nth (ast:cad-get 'target-index pair) target-ordered)
          source-route (ast:cad-get 'route source-state) target-route (ast:cad-get 'route target-state)
          settings (ast:match-settings (ast:cad-get 'settings source-state) source-route target-route pair parity)
          landmarks (ast:match-landmarks (ast:cad-get 'landmarks source-state) source-route target-route pair))
    (if check-landmarks
      (foreach original (ast:cad-get 'landmarks target-state)
        (ast:cad-require (vl-some '(lambda (item) (< (abs (- (ast:match-global target-route original)
          (ast:match-global target-route item))) 1e-7)) landmarks)
          "This guide has a landmark that is not on the source. Add the corresponding source landmark or remove it before matching.")))
    (setq target-state (ast:cad-put 'settings settings (ast:cad-put 'landmarks landmarks
      (ast:cad-put 'record (ast:cad-put 'attachment-route target-route (ast:cad-get 'record target-state)) target-state)))
          mapped-states (cons (cons (ast:cad-get 'guide target-state) target-state) mapped-states)
          guide-pairs (cons (cons (ast:cad-get 'guide source-state) (ast:cad-get 'guide target-state)) guide-pairs)))
  (setq target-states (mapcar '(lambda (state) (cdr (assoc (ast:cad-get 'guide state) mapped-states))) target-states))
  (ast:cad-set-check target-states restore)
  (setq connections (ast:match-connections target-states))
  (ast:match-topology source-states source-connections target-states connections guide-pairs transform)
  (list (cons 'owner target) (cons 'states target-states) (cons 'connections connections)
    (cons 'transform transform) (cons 'record (ast:cad-put 'parity parity record))))

(defun ast:match-write-group (owner record / state member)
  (setq state (ast:cad-read-base owner))
  (foreach member (ast:cad-get 'members state)
    (ast:cad-require (and member (entget member)) "A matching guide was deleted. Repair the link before generating.")
    (ast:match-write-record member record)))
(defun ast:match-key (members / result owner state states record member)
  (foreach owner members
    (if (and owner (entget owner))
      (progn
        (setq state (ast:cad-read-base owner) record (ast:match-record owner) states nil)
        (foreach member (ast:cad-get 'members state)
          (if (and member (entget member))
            (progn
              (setq state (ast:cad-read-base member))
              (setq states (append states (list (list (cdr (assoc 5 (entget member))) (ast:cad-get 'route state)
                (ast:cad-get 'settings state) (ast:cad-get 'landmarks state))))))
            (setq states (append states '(missing)))))
        (setq result (append result (list (list (cdr (assoc 5 (entget owner))) states
          (ast:cad-get 'connections (ast:cad-read-base owner)) (ast:cad-get 'face record)
          (ast:cad-get 'target-reversed record) (ast:cad-get 'target-phase record) (ast:cad-get 'source-phase record)
          (ast:cad-get 'source-index record))))))
      (setq result (append result '(missing))))) result)
(defun ast:match-any-stale (members / owner member stale)
  (foreach owner members
    (if (and owner (entget owner))
      (foreach member (ast:cad-get 'members (ast:cad-read-base owner))
        (if (or (null member) (null (entget member)) (ast:cad-get 'stale (ast:cad-read-base member))) (setq stale T)))
      (setq stale T))) stale)
(defun ast:match-placement-conflict-p (members / owner member conflict)
  (foreach owner members
    (if (and owner (entget owner))
      (foreach member (ast:cad-get 'members (ast:cad-read-base owner))
        (if (and member (entget member) (ast:cad-get 'placement-conflict (ast:cad-read-base member)))
          (setq conflict T)))))
  conflict)
(defun ast:match-decorate (state / info key result)
  (setq info (ast:match-info (ast:cad-get 'guide state)))
  (if (ast:cad-get 'active info)
    (progn
      (setq result (vl-catch-all-apply 'ast:match-key (list (ast:cad-get 'members info))))
      (if (or (ast:cad-get 'error info) (vl-catch-all-error-p result) (ast:match-any-stale (ast:cad-get 'members info))
              (not (equal result (ast:cad-get 'generated-key (ast:cad-get 'record info)) 1e-8)))
        (setq state (ast:cad-put 'stale T state)))
      (if (and (not (ast:cad-get 'error info)) (not (vl-catch-all-error-p result))
               (ast:match-placement-conflict-p (ast:cad-get 'members info)))
        (setq state (ast:cad-put 'placement-conflict T state)))))
  (ast:cad-put 'match-error (ast:cad-get 'error info)
    (ast:cad-put 'match-role (ast:cad-get 'role info)
      (ast:cad-put 'match-source (ast:cad-get 'source info) (ast:cad-put 'matching info state)))))

(defun ast:match-suffix (number / suffix)
  (setq suffix "")
  (while (> number 0)
    (setq number (1- number) suffix (strcat (chr (+ 65 (rem number 26))) suffix)
          number (fix (/ number 26))))
  suffix)
(defun ast:match-name-free-p (name owner / output selection index entity record occupied)
  (setq output (ast:cad-get 'link (ast:cad-record owner)))
  (if (and (tblsearch "BLOCK" name)
           (not (and output (entget output) (= name (cdr (assoc 2 (entget output)))))))
    (setq occupied T))
  (if (and (not occupied) (setq selection (ssget "_X" '((0 . "LINE,ARC,CIRCLE,LWPOLYLINE")))))
    (progn
      (setq index 0)
      (while (and (not occupied) (< index (sslength selection)))
        (setq entity (ssname selection index) record (ast:cad-record entity) index (1+ index))
        (if (and (not (equal entity owner)) (equal name (ast:cad-get 'stitch-id record))
                 (equal (ast:cad-get 'stitch-owner record) (cdr (assoc 5 (entget entity)))))
          (setq occupied T)))))
  (not occupied))
(defun ast:match-name-family (members refresh / prefix owner state record name suffix number member)
  (setq prefix (strcat (ast:cad-ensure-stitch-id (car members)) "-"))
  (foreach owner (cdr members)
    (setq state (ast:cad-read-base owner) record (ast:cad-record owner) name (ast:cad-get 'stitch-id record)
          suffix (if (and (= (type name) 'STR) (= (substr name 1 (strlen prefix)) prefix))
            (substr name (1+ (strlen prefix)))))
    (if (not (and suffix (> (strlen suffix) 0)
            (vl-every '(lambda (code) (and (>= code 65) (<= code 90))) (vl-string->list suffix))
            (equal (ast:cad-get 'stitch-owner record) (cdr (assoc 5 (entget owner))))
            (ast:match-name-free-p name owner)))
      (progn
        (setq number 1 name (strcat prefix (ast:match-suffix number)))
        (while (not (ast:match-name-free-p name owner))
          (setq number (1+ number) name (strcat prefix (ast:match-suffix number))))
        (foreach member (ast:cad-get 'members state)
          (setq record (ast:cad-record member))
          (ast:cad-write-record member
            (ast:cad-put 'stitch-id name (ast:cad-put 'stitch-owner (cdr (assoc 5 (entget owner)))
              (vl-remove-if '(lambda (item) (eq (car item) 'link)) record))) (ast:cad-get 'link record)))
        (if refresh (ast:cad-update-markers state (ast:cad-get 'settings state) (ast:cad-get 'landmarks state)))))))

(defun ast:match-link-write (source-states source-record plans / plan state members record)
  (setq members (ast:cad-get 'members source-record))
  (foreach state source-states (ast:cad-save-inputs-inner state (ast:cad-get 'settings state) (ast:cad-get 'landmarks state)))
  (ast:match-write-group (car members) source-record)
  (foreach plan plans
    (foreach state (ast:cad-get 'states plan) (ast:cad-save-inputs-inner state (ast:cad-get 'settings state) (ast:cad-get 'landmarks state)))
    (setq record (ast:cad-put 'members members (ast:cad-put 'primary (car members) (ast:cad-get 'record plan))))
    (ast:match-write-group (ast:cad-get 'owner plan) record)
    (ast:cad-inject "match-link-copy"))
  (ast:match-name-family members T)
  (list '(ok . T) (cons 'source (car members)) (cons 'targets (cdr members))))
(defun ast:match-link-inner (source target parity target-reversed / source-state target-state source-info target-info source-owner target-owner source-states source-record source-anchor source-phase source-connections target-record members plans peer phase reversed)
  (ast:cad-require (member parity '(1 -1)) "Choose Front or Back for the matched guide.")
  (setq source-state (ast:cad-read-base source) target-state (ast:cad-read-base target)
        source-info (ast:match-info-inner source) target-info (ast:match-info-inner target)
        source-owner (ast:cad-get 'owner source-info) target-owner (ast:cad-get 'owner target-info))
  (ast:cad-require (not (ast:cad-get 'error source-info)) (ast:cad-get 'error source-info))
  (ast:cad-require (not (eq (ast:cad-get 'role source-info) 'copy)) "Select the original source stitch line to add another matched guide.")
  (ast:cad-require (not (ast:cad-get 'active target-info)) "This guide already belongs to a matching set. Unlink it before matching it again.")
  (ast:cad-require (not (equal source-owner target-owner)) "Choose guides outside this stitch line.")
  (setq source-states (ast:match-states source-owner nil nil nil))
  (ast:cad-set-check source-states nil)
  (setq source-connections (ast:match-connections source-states)
        source-record (ast:cad-get 'record source-info) source-anchor (ast:cad-get 'link source-record))
  (if (null source-anchor) (setq source-anchor (ast:cad-get 'guide source-state)))
  (setq source-phase (if (assoc 'source-phase source-record) (ast:cad-get 'source-phase source-record)
    (ast:g-get 'phase (ast:cad-get 'settings (ast:cad-read-base source-anchor)) 0.0)))
  (setq members (if (ast:cad-get 'active source-info) (ast:cad-get 'members source-info) (list source-owner))
        members (append members (list target-owner))
        reversed (if (and target-reversed (listp target-reversed))
          (if (assoc 'reversed target-reversed) (ast:cad-get 'reversed target-reversed) 'auto) target-reversed)
        phase (if (and target-reversed (listp target-reversed)) (ast:cad-get 'phase target-reversed)))
  (if (null phase) (setq phase (ast:g-get 'phase (ast:cad-get 'settings target-state) 0.0)))
  (setq source-record (list '(schema . 1) (cons 'primary source-owner) (cons 'members members) (cons 'link source-anchor) (cons 'source-phase source-phase))
        target-record (list '(schema . 1) (cons 'primary source-owner) (cons 'members members)
          (cons 'link (ast:cad-get 'guide target-state)) (cons 'parity parity)
          (cons 'source-index (vl-position (ast:cad-get 'guide source-state) (mapcar '(lambda (state) (ast:cad-get 'guide state)) source-states)))
          (cons 'source-phase (ast:g-get 'phase (ast:cad-get 'settings source-state) 0.0))
          (cons 'face (* parity (ast:g-get 'handedness (ast:cad-get 'settings source-state) 1)))
          (cons 'target-reversed reversed) (cons 'target-phase phase)))
  (foreach peer (cdr members)
    (setq plans (append plans (list (ast:match-target-plan source-states source-connections source-anchor source-phase peer
      (if (equal peer target-owner) target-record (ast:match-record peer)) (equal peer target-owner) nil)))))
  (ast:cad-transaction 'ast:match-link-write (list source-states source-record plans)))
(defun ast:match-link (source target parity target-reversed)
  (ast:cad-catch 'ast:match-link-inner (list source target parity target-reversed)))

(defun ast:match-generate-write (source-states source-connections solution plans members / result plan state record key selected-output owner)
  (ast:match-name-family members nil)
  (if (> (length source-states) 1)
    (setq result (ast:cad-write-set-inner source-states source-connections solution))
    (setq state (car source-states) result (ast:cad-write-inner state (ast:cad-get 'settings state) (ast:cad-get 'landmarks state) solution)))
  (foreach plan plans
    (setq state (car (ast:cad-get 'states plan)))
    (if (> (length (ast:cad-get 'states plan)) 1)
      (ast:cad-write-set-inner (ast:cad-get 'states plan) (ast:cad-get 'connections plan) (ast:cad-get 'solution plan))
      (ast:cad-write-inner state (ast:cad-get 'settings state) (ast:cad-get 'landmarks state) (ast:cad-get 'solution plan)))
    (ast:match-write-group (ast:cad-get 'owner plan) (ast:cad-get 'record plan))
    (ast:cad-inject "match-copy-output"))
  (setq key (ast:match-key members))
  (foreach owner members
    (ast:match-write-group owner (ast:cad-put 'generated-key key (ast:match-record owner))))
  (ast:cad-inject "match-family-metadata")
  result)
(defun ast:match-generate-inner (entity settings landmarks restore / info source selected source-states connections solution solved plans target plan source-anchor result selected-owner)
  (setq info (ast:match-info-inner entity) selected (ast:cad-get 'guide (ast:cad-read-base entity))
        source (ast:cad-get 'source info) selected-owner (ast:cad-get 'owner info))
  (ast:cad-require (ast:cad-get 'active info) "This stitch line has no matched-guide link.")
  (ast:cad-require (not (ast:cad-get 'error info)) (ast:cad-get 'error info))
  (setq source-states (ast:match-states source (if (eq (ast:cad-get 'role info) 'source) selected) settings landmarks))
  (ast:cad-set-check source-states restore)
  (setq connections (ast:match-connections source-states))
  (if (> (length source-states) 1)
    (setq solution (ast:g-solve-set (ast:cad-set-paths source-states) connections))
    (setq solution (ast:g-solve (ast:cad-get 'route (car source-states))
      (ast:cad-get 'settings (car source-states)) (ast:cad-get 'landmarks (car source-states)))))
  (ast:cad-require (ast:cad-get 'ok solution) (ast:cad-get 'error solution))
  (setq source-anchor (ast:cad-get 'link (ast:match-record source)))
  (foreach target (ast:cad-get 'targets info)
    (setq plan (ast:match-target-plan source-states connections source-anchor (ast:cad-get 'source-phase (ast:match-record source)) target (ast:match-record target) nil restore)
          plans (append plans (list (ast:cad-put 'solution (ast:m-solution solution (ast:cad-get 'transform plan)) plan)))))
  (setq result (ast:cad-transaction 'ast:match-generate-write
    (list source-states connections solution plans (ast:cad-get 'members info))))
  (if (ast:cad-get 'ok result)
    (setq result (ast:cad-put 'output (ast:cad-get 'output (ast:cad-read-base selected-owner)) result))) result)
(defun ast:match-generate (entity settings landmarks restore)
  (ast:cad-catch 'ast:match-generate-inner (list entity settings landmarks restore)))

(defun ast:match-unlink-write (owner members source / member state record guide)
  (if owner
    (foreach member (ast:cad-get 'members (ast:cad-read-base owner)) (ast:match-remove-record member)))
  (foreach member members
    (if (and member (entget member))
      (if (and (= (length members) 1) (equal member source))
        (foreach guide (ast:cad-get 'members (ast:cad-read-base member)) (ast:match-remove-record guide))
        (ast:match-write-group member (ast:cad-put 'generated-key nil
          (ast:cad-put 'members members (ast:match-record member)))))))
  (list '(ok . T)))
(defun ast:match-unlink-inner (entity / info owner members peer state member source)
  (setq info (ast:match-info-inner entity) owner (ast:cad-get 'owner info))
  (ast:cad-require (or (eq (ast:cad-get 'role info) 'copy) (ast:cad-get 'repairable info))
    "Select a matching copy to unlink it from its source.")
  (setq source (ast:cad-get 'source info)
        members (if (and source (entget source)) (ast:cad-get 'members (ast:match-record source)) (ast:cad-get 'members info)))
  (if (ast:cad-get 'repairable info) (setq owner nil) (setq members (vl-remove owner members)))
  (setq members (vl-remove-if-not '(lambda (member) (and member (entget member))) members))
  (foreach peer (cons owner members)
    (if (and peer (entget peer))
      (foreach member (ast:cad-get 'members (ast:cad-read-base peer))
        (if (and member (entget member))
          (ast:cad-require (ast:cad-layer-unlocked-p (cdr (assoc 8 (entget member)))) "Unlock the matching guides before unlinking.")))))
  (ast:cad-transaction 'ast:match-unlink-write (list owner members source)))
(defun ast:match-unlink (entity) (ast:cad-catch 'ast:match-unlink-inner (list entity)))

(defun ast:match-face-record (record / anchor)
  (setq anchor (ast:cad-get 'link record))
  (if (and anchor (entget anchor) (ast:cad-get 'closed (ast:cad-get 'route (ast:cad-read-base anchor))))
    (setq record (ast:cad-put 'target-reversed 'auto record))) record)
(defun ast:match-face-write (info states face / state owner record target source-face)
  (if (eq (ast:cad-get 'role info) 'copy)
    (progn
      (setq owner (ast:cad-get 'owner info) record (ast:match-record owner)
            source-face (ast:g-get 'handedness (ast:cad-get 'settings (ast:cad-read-base (ast:cad-get 'source info))) 1))
      (ast:match-write-group owner (ast:match-face-record (ast:cad-put 'generated-key nil
        (ast:cad-put 'face face (ast:cad-put 'parity (* face source-face) record))))))
    (progn
      (foreach state states
        (ast:cad-save-inputs-inner state (ast:cad-put 'handedness face (ast:cad-get 'settings state)) (ast:cad-get 'landmarks state)))
      (foreach target (ast:cad-get 'targets info)
        (setq record (ast:match-record target))
        (ast:match-write-group target (ast:match-face-record (ast:cad-put 'generated-key nil
          (ast:cad-put 'parity (* face (ast:g-get 'face record 1)) record)))))))
  (list '(ok . T)))
(defun ast:match-set-face-inner (entity face / info states peer member)
  (ast:cad-require (member face '(1 -1)) "Choose Front or Back.")
  (setq info (ast:match-info-inner entity))
  (ast:cad-require (not (ast:cad-get 'error info)) (ast:cad-get 'error info))
  (setq states (ast:match-raw-states (ast:cad-get 'owner info)))
  (foreach peer (if (ast:cad-get 'active info) (ast:cad-get 'members info) (list (ast:cad-get 'owner info)))
    (foreach member (ast:cad-get 'members (ast:cad-read-base peer))
      (ast:cad-require (ast:cad-layer-unlocked-p (cdr (assoc 8 (entget member)))) "Unlock the matching guide layers before changing the face.")))
  (ast:cad-transaction 'ast:match-face-write (list info states face)))
(defun ast:match-set-face (entity face) (ast:cad-catch 'ast:match-set-face-inner (list entity face)))
(princ)
