;;; Explicitly connected physical stitch paths. Load after autostitch-geometry.lsp.
;;; Source attachments remain separate from derived finite edges and shared openings.
(defun ast:n-put (key value record / pair)
  (if (setq pair (assoc key record)) (subst (cons key value) pair record) (cons (cons key value) record)))
(defun ast:n-path (id paths)
  (vl-some '(lambda (item) (if (= (ast:g-get 'id item nil) id) item)) paths))
(defun ast:n-station (primitive point / angle)
  (if (= (ast:g-get 'kind primitive nil) 'line)
    (ast:g-clamp (ast:g-dot (ast:g-sub point (ast:g-point primitive 0.0)) (ast:g-tangent primitive 0.0)) 0.0 (ast:g-length primitive))
    (progn
      (setq angle (* (ast:g-sign (ast:g-get 'sweep primitive 0))
        (- (atan (- (cadr point) (cadr (ast:g-get 'center primitive nil))) (- (car point) (car (ast:g-get 'center primitive nil)))) (ast:g-get 'start-angle primitive 0))))
      (while (< angle -1e-9) (setq angle (+ angle (* 2.0 pi))))
      (while (> angle (+ (* 2.0 pi) 1e-9)) (setq angle (- angle (* 2.0 pi))))
      (* (ast:g-get 'radius primitive 0) (max 0.0 angle)))))
(defun ast:n-unique-points (points / result point)
  (foreach point points (if (not (vl-some '(lambda (item) (< (ast:g-dist point item) 1e-8)) result)) (setq result (cons point result))))
  (reverse result))
(defun ast:n-interior (primitive point / station)
  (and (ast:g-point-on primitive point) (setq station (ast:n-station primitive point)) (> station 1e-8) (< station (- (ast:g-length primitive) 1e-8))))
(defun ast:n-hits (aa bb / hit points point overlap)
  (setq hit (ast:g-intersections (ast:g-support aa) (ast:g-support bb)))
  (if (ast:g-get 'coincident hit nil)
    (progn
      (foreach point (list (ast:g-point aa 0.0) (ast:g-point aa (ast:g-length aa))
                          (ast:g-point bb 0.0) (ast:g-point bb (ast:g-length bb)))
        (if (and (ast:g-point-on aa point) (ast:g-point-on bb point)) (setq points (cons point points)))
        (if (and (ast:g-point-on aa point) (ast:g-point-on bb point) (or (ast:n-interior aa point) (ast:n-interior bb point))) (setq overlap T)))
      (if (or (ast:n-interior bb (ast:g-point aa (/ (ast:g-length aa) 2.0)))
              (ast:n-interior aa (ast:g-point bb (/ (ast:g-length bb) 2.0)))) (setq overlap T)))
    (foreach point (ast:g-get 'points hit nil)
      (if (and (ast:g-point-on aa point) (ast:g-point-on bb point)) (setq points (cons point points)))))
  ;; A tangent quadratic can lose an exact endpoint through roundoff. Preserve
  ;; finite endpoints that both guides contain, using the existing join tolerance.
  (foreach point (list (ast:g-point aa 0.0) (ast:g-point aa (ast:g-length aa))
                      (ast:g-point bb 0.0) (ast:g-point bb (ast:g-length bb)))
    (if (and (ast:g-point-on aa point) (ast:g-point-on bb point)) (setq points (cons point points))))
  (list (cons 'points (ast:n-unique-points (reverse points))) (cons 'overlap overlap)))
(defun ast:n-route-error (route / primitives previous primitive error)
  (setq primitives (ast:g-get 'primitives route nil))
  (if (null primitives) (setq error "No usable stitch line was found. Select a line or curve."))
  (foreach primitive primitives
    (if (null error) (setq error (ast:g-primitive-error primitive)))
    (if (and (null error) previous (> (ast:g-dist (ast:g-point previous (ast:g-length previous)) (ast:g-point primitive 0.0)) 1e-8))
      (setq error "The guide has a break between segments. Join their endpoints or stitch them as separate lines."))
    (setq previous primitive))
  (if (and (null error) (ast:g-get 'closed route nil) (> (ast:g-dist (ast:g-point (car primitives) 0.0) (ast:g-point previous (ast:g-length previous))) 1e-8))
    (setq error "The closed guide has a gap at its join. Close that gap before generating stitches.")) error)
(defun ast:n-incidence (path index primitive point route)
  (list (cons 'path path) (cons 'primitive index) (cons 'station (ast:n-station primitive point)) (cons 'source-route route)))
(defun ast:g-connect-candidates (route-a route-b / error aa bb ii jj hit point nodes existing incidences node)
  (setq error (ast:n-route-error route-a) ii 0)
  (if (null error) (setq error (ast:n-route-error route-b)))
  (if (null error)
    (foreach aa (ast:g-get 'primitives route-a nil)
      (setq jj 0)
      (foreach bb (ast:g-get 'primitives route-b nil)
        (setq hit (ast:n-hits aa bb))
        (if (ast:g-get 'overlap hit nil) (setq error "The guides overlap along a length. Trim the overlap before using Connect stitch lines."))
        (foreach point (ast:g-get 'points hit nil)
          (setq existing (vl-some '(lambda (item) (if (< (ast:g-dist point (ast:g-get 'point item nil)) 1e-8) item)) nodes)
                incidences (list (ast:n-incidence 0 ii aa point route-a) (ast:n-incidence 1 jj bb point route-b)))
          (if existing
            (progn
              (foreach node (ast:g-get 'incidences existing nil)
                (if (not (vl-some '(lambda (item) (and (= (ast:g-get 'path item nil) (ast:g-get 'path node nil)) (= (ast:g-get 'primitive item nil) (ast:g-get 'primitive node nil)))) incidences))
                  (setq incidences (cons node incidences))))
              (setq nodes (subst (ast:n-put 'incidences incidences existing) existing nodes)))
            (setq nodes (append nodes (list (list (cons 'id (length nodes)) (cons 'point point) (cons 'incidences incidences)))))))
        (setq jj (1+ jj)))
      (setq ii (1+ ii))))
  (if error (ast:g-error error) (list '(ok . T) (cons 'connections nodes))))

;;; Root-side signatures distinguish the two roots without a nearest-point fallback.
(defun ast:n-root-sign (aa bb point / value)
  (cond
    ((and (= (ast:g-get 'kind aa nil) 'line) (= (ast:g-get 'kind bb nil) 'line)) 0)
    ((= (ast:g-get 'kind aa nil) 'line)
      (setq value (ast:g-dot (ast:g-sub point (ast:g-get 'center bb nil)) (ast:g-tangent aa 0.0))))
    ((= (ast:g-get 'kind bb nil) 'line) (setq value (ast:g-dot (ast:g-sub point (ast:g-get 'center aa nil)) (ast:g-tangent bb 0.0))))
    (T (setq value (ast:g-cross (ast:g-sub (ast:g-get 'center bb nil) (ast:g-get 'center aa nil)) (ast:g-sub point (ast:g-get 'center aa nil))))))
  (if value (cond ((> value 1e-8) 1) ((< value -1e-8) -1) (T 0)) 0))
(defun ast:n-transform-point (point origin target old-axis new-axis parity / delta xx yy)
  (setq delta (ast:g-sub point origin) xx (ast:g-dot delta old-axis) yy (* parity (ast:g-dot delta (ast:g-left old-axis))))
  (ast:g-add target (ast:g-add (ast:g-mul new-axis xx) (ast:g-mul (ast:g-left new-axis) yy))))
(defun ast:n-common-move (old-primitives new-primitives point / aa bb origin target old-axis new-axis parity valid result old-item new-item fraction)
  (setq aa (car old-primitives) bb (car new-primitives) origin (ast:g-point aa 0.0) target (ast:g-point bb 0.0)
        old-axis (ast:g-tangent aa 0.0) new-axis (ast:g-tangent bb 0.0))
  (foreach parity '(1 -1)
    (setq valid T old-item old-primitives new-item new-primitives)
    (while (and valid old-item new-item)
      (setq aa (car old-item) bb (car new-item))
      (if (> (abs (- (ast:g-length aa) (ast:g-length bb))) 1e-8) (setq valid nil))
      (foreach fraction '(0.0 0.25 0.5 0.75 1.0)
        (if (> (ast:g-dist (ast:n-transform-point (ast:g-point aa (* fraction (ast:g-length aa))) origin target old-axis new-axis parity)
                          (ast:g-point bb (* fraction (ast:g-length bb)))) 1e-8) (setq valid nil)))
      (setq old-item (cdr old-item) new-item (cdr new-item)))
    (if valid (setq result (ast:n-transform-point point origin target old-axis new-axis parity)))) result)
(defun ast:n-translation (old-primitives new-primitives point / aa bb delta valid forward backward fraction)
  ;; Native traversal and a full circle's parameter origin are not physical anchors.
  (setq aa (car old-primitives) bb (car new-primitives)
        delta (ast:g-sub (if (= (ast:g-get 'kind bb nil) 'line) (ast:g-point bb (/ (ast:g-length bb) 2.0)) (ast:g-get 'center bb nil))
                         (if (= (ast:g-get 'kind aa nil) 'line) (ast:g-point aa (/ (ast:g-length aa) 2.0)) (ast:g-get 'center aa nil))) valid T)
  (while (and valid old-primitives new-primitives)
    (setq aa (car old-primitives) bb (car new-primitives))
    (if (or (/= (ast:g-get 'kind aa nil) (ast:g-get 'kind bb nil)) (> (abs (- (ast:g-length aa) (ast:g-length bb))) 1e-8))
      (setq valid nil)
      (if (and (= (ast:g-get 'kind aa nil) 'arc) (ast:g-near (abs (ast:g-get 'sweep aa 0)) (* 2.0 pi)) (ast:g-near (abs (ast:g-get 'sweep bb 0)) (* 2.0 pi)))
        (if (> (ast:g-dist (ast:g-add (ast:g-get 'center aa nil) delta) (ast:g-get 'center bb nil)) 1e-8) (setq valid nil))
        (progn
          (setq forward T backward T)
          (foreach fraction '(0.0 0.25 0.5 0.75 1.0)
            (if (> (ast:g-dist (ast:g-add (ast:g-point aa (* fraction (ast:g-length aa))) delta) (ast:g-point bb (* fraction (ast:g-length bb)))) 1e-8) (setq forward nil))
            (if (> (ast:g-dist (ast:g-add (ast:g-point aa (* fraction (ast:g-length aa))) delta) (ast:g-point bb (* (- 1.0 fraction) (ast:g-length bb)))) 1e-8) (setq backward nil)))
          (if (not (or forward backward)) (setq valid nil)))))
    (setq old-primitives (cdr old-primitives) new-primitives (cdr new-primitives)))
  (if valid (ast:g-add point delta)))
(defun ast:g-resolve-connections (paths connections / error path route node incidence index primitive old-route old-primitive current previous records candidates hit point chosen expected valid pair-a pair-b old-a old-b sign-old sign-new refreshed result all-old all-new same-support translated signature-current direction)
  (foreach path paths (if (null error) (setq error (ast:n-route-error (ast:g-get 'route path nil)))))
  (foreach node connections
    (if (null error)
      (progn
        (setq current nil previous nil records nil all-old nil all-new nil candidates nil chosen nil)
        (if (not (ast:g-pointp (ast:g-get 'point node nil))) (setq error "The saved junction position is invalid. Use Disconnect line, then Connect stitch lines again."))
        (foreach incidence (ast:g-get 'incidences node nil)
          (setq path (ast:n-path (ast:g-get 'path incidence nil) paths) route (ast:g-get 'route path nil)
                index (ast:g-get 'primitive incidence nil) old-route (ast:g-get 'source-route incidence nil))
          (if (not (and path (numberp index) (= index (fix index)) (>= index 0) (< index (length (ast:g-get 'primitives route nil)))))
            (setq error "A line changed at its saved junction. Use Disconnect line, then Connect stitch lines again.")
            (progn
              (setq primitive (nth index (ast:g-get 'primitives route nil)) old-primitive (if old-route (nth index (ast:g-get 'primitives old-route nil)) primitive))
              (if (and old-route (or (/= (length (ast:g-get 'primitives old-route nil)) (length (ast:g-get 'primitives route nil)))
                                    (/= (ast:g-get 'kind primitive nil) (ast:g-get 'kind old-primitive nil))))
                (setq error "A line changed shape at its saved junction. Use Disconnect line, then Connect stitch lines again."))
              (setq current (append current (list primitive)) previous (append previous (list old-primitive)) records (append records (list incidence))
                    all-old (append all-old (if old-route (ast:g-get 'primitives old-route nil) (ast:g-get 'primitives route nil)))
                    all-new (append all-new (ast:g-get 'primitives route nil))))))
        (if (< (length current) 2) (setq error "This junction no longer joins two lines. Disconnect the line and reconnect the intended guides."))
        (if (null error)
          (progn
            (setq pair-a current)
            (while (and pair-a (null candidates))
              (setq pair-b (cdr pair-a))
              (while (and pair-b (null candidates))
                (setq hit (ast:n-hits (car pair-a) (car pair-b)))
                (if (ast:g-get 'overlap hit nil) (setq error "The guides now overlap along a length. Trim the overlap, then disconnect and reconnect the affected line."))
                (setq candidates (ast:g-get 'points hit nil) pair-b (cdr pair-b)))
              (setq pair-a (cdr pair-a)))
            (setq candidates (vl-remove-if-not '(lambda (candidate) (vl-every '(lambda (item) (ast:g-point-on item candidate)) current)) candidates)
                  expected (ast:n-common-move all-old all-new (ast:g-get 'point node nil))
                  translated (ast:n-translation all-old all-new (ast:g-get 'point node nil)))
            (if translated
              (if (and expected (> (ast:g-dist expected translated) 1e-8))
                (setq error "The edited lines have more than one possible match for this junction. Disconnect and reconnect the affected line.")
                (setq expected translated)))
            ;; Reversing native entity traversal does not change its physical root.
            ;; Common motion takes priority: its other root may occupy the old point.
            (if (null expected)
              (progn
                (setq same-support T pair-a current old-a previous)
                (while pair-a
                  (if (not (ast:g-get 'coincident (ast:g-intersections (ast:g-support (car pair-a)) (ast:g-support (car old-a))) nil)) (setq same-support nil))
                  (setq pair-a (cdr pair-a) old-a (cdr old-a)))
                (if same-support (setq expected (ast:g-get 'point node nil)))))
            (if expected
              (setq candidates (vl-remove-if-not '(lambda (candidate) (< (ast:g-dist candidate expected) 1e-8)) candidates))
              (progn
                (setq refreshed nil signature-current nil pair-a current old-a previous)
                (while pair-a
                  (setq primitive (car pair-a))
                  (if (= (ast:g-get 'kind primitive nil) 'line)
                    (progn
                      (setq direction (ast:g-dot (ast:g-tangent (car old-a) 0.0) (ast:g-tangent primitive 0.0)))
                      (if (< direction 0.0)
                        (if (< (abs (ast:g-cross (ast:g-tangent (car old-a) 0.0) (ast:g-tangent primitive 0.0))) 1e-10)
                          (setq primitive (ast:g-reverse-primitive primitive))
                          (setq error "The line's new direction does not identify the saved junction. Disconnect and reconnect the line.")))))
                  (setq signature-current (append signature-current (list primitive)) pair-a (cdr pair-a) old-a (cdr old-a)))
                (foreach point candidates
                  (setq valid T pair-a signature-current old-a previous)
                  (while pair-a
                    (setq pair-b (cdr pair-a) old-b (cdr old-a))
                    (while pair-b
                      (setq sign-old (ast:n-root-sign (car old-a) (car old-b) (ast:g-get 'point node nil))
                            sign-new (ast:n-root-sign (car pair-a) (car pair-b) point))
                      (if (and (= (ast:g-get 'kind (car old-a) nil) 'arc) (= (ast:g-get 'kind (car old-b) nil) 'arc)
                               (<= (ast:g-dot (ast:g-sub (ast:g-get 'center (car old-b) nil) (ast:g-get 'center (car old-a) nil))
                                             (ast:g-sub (ast:g-get 'center (car pair-b) nil) (ast:g-get 'center (car pair-a) nil))) 0.0))
                        (setq valid nil))
                      (if (and (/= sign-old 0) (/= sign-old sign-new)) (setq valid nil))
                      (setq pair-b (cdr pair-b) old-b (cdr old-b)))
                    (setq pair-a (cdr pair-a) old-a (cdr old-a)))
                  (if valid (setq refreshed (cons point refreshed))))
                (setq candidates refreshed)))
            (if (/= (length candidates) 1)
              (if (null error) (setq error "The saved junction no longer matches a single intersection. Disconnect and reconnect the affected line."))
              (progn
                (setq chosen (car candidates) refreshed nil)
                (foreach incidence records
                  (setq path (ast:n-path (ast:g-get 'path incidence nil) paths) route (ast:g-get 'route path nil) index (ast:g-get 'primitive incidence nil)
                        primitive (nth index (ast:g-get 'primitives route nil))
                        refreshed (append refreshed (list (ast:n-put 'source-route route (ast:n-put 'station (ast:n-station primitive chosen) incidence))))))
                (setq result (append result (list (ast:n-put 'point chosen (ast:n-put 'incidences refreshed node))))))))))))
  (if error (ast:g-error error) (list '(ok . T) (cons 'connections result))))

;;; Prepare finite source geometry using the existing range/normalization rules.
(defun ast:n-prepare (path / route settings error range normalized primitives primitive)
  (setq route (ast:g-get 'route path nil) settings (ast:g-get 'settings path nil)
        error (ast:n-route-error route))
  (if (null error) (setq error (ast:g-profile-error settings)))
  (if (null error)
    (progn
      (setq range (ast:g-range (ast:g-get 'primitives route nil) (ast:g-get 'landmarks path nil) settings (ast:g-get 'closed route nil)))
      (if (not (ast:g-get 'ok range nil)) (setq error (ast:g-get 'error range nil))
        (progn
          (setq normalized (ast:g-normalize (ast:g-get 'primitives range nil) (ast:g-get 'landmarks range nil) (ast:g-get 'reverse settings nil)))
          (if (not (ast:g-get 'ok normalized nil)) (setq error (ast:g-get 'error normalized nil))
            (progn
              (setq primitives (ast:g-get 'primitives normalized nil))
              (foreach primitive primitives
                (if (and (= (ast:g-get 'kind primitive nil) 'arc) (> (ast:g-get 'pitch settings 3.0) (* 2.0 (ast:g-get 'radius primitive 0))))
                  (setq error "The pitch is too large for this curve. Reduce the pitch or increase the curve radius.")))))))))
  (if error (ast:g-error error) (list '(ok . T) (cons 'id (ast:g-get 'id path nil)) (cons 'settings settings)
    (cons 'primitives primitives) (cons 'landmarks (ast:g-get 'landmarks normalized nil)) (cons 'closed (ast:g-get 'closed route nil)))))
(defun ast:n-declared (point id-a id-b connections)
  (and
    (vl-some '(lambda (node)
      (and (< (ast:g-dist point (ast:g-get 'point node nil)) 1e-8)
        (vl-some '(lambda (inc) (= id-a (ast:g-get 'path inc nil))) (ast:g-get 'incidences node nil)))) connections)
    (vl-some '(lambda (node)
      (and (< (ast:g-dist point (ast:g-get 'point node nil)) 1e-8)
        (vl-some '(lambda (inc) (= id-b (ast:g-get 'path inc nil))) (ast:g-get 'incidences node nil)))) connections)))
(defun ast:n-crossing-error (prepared connections / entries path primitive index entry-a entry-b tail rest hit point allowed error same-path count)
  (foreach path prepared
    (setq index 0)
    (foreach primitive (ast:g-get 'primitives path nil)
      (setq entries (append entries (list (list path index primitive))) index (1+ index))))
  (setq tail entries)
  (while (and tail (null error))
    (setq entry-a (car tail) rest (cdr tail))
    (while (and rest (null error))
      (setq entry-b (car rest) hit (ast:n-hits (caddr entry-a) (caddr entry-b))
            same-path (= (ast:g-get 'id (car entry-a) nil) (ast:g-get 'id (car entry-b) nil)))
      (if (ast:g-get 'overlap hit nil) (setq error "The stitch guides overlap along a length. Trim the overlap before connecting them."))
      (foreach point (ast:g-get 'points hit nil)
        (setq allowed nil)
        (if same-path
          (progn
            (setq count (length (ast:g-get 'primitives (car entry-a) nil)))
            (if (and (= (cadr entry-b) (1+ (cadr entry-a))) (< (ast:g-dist point (ast:g-point (caddr entry-a) (ast:g-length (caddr entry-a)))) 1e-8)) (setq allowed T))
            (if (and (ast:g-get 'closed (car entry-a) nil) (= (cadr entry-a) 0) (= (cadr entry-b) (1- count))
                     (< (ast:g-dist point (ast:g-point (caddr entry-a) 0.0)) 1e-8)) (setq allowed T))))
        (if (not (or allowed (ast:n-declared point (ast:g-get 'id (car entry-a) nil) (ast:g-get 'id (car entry-b) nil) connections)))
          (setq error "These connected lines meet at another point. Use Connect stitch lines to include that intersection.")))
      (setq rest (cdr rest)))
    (setq tail (cdr tail))) error)
(defun ast:n-split (prepared connections / edges next-id path primitive index stations node point markers marker sorted start finish local-marks)
  (setq next-id 0)
  (foreach path prepared
    (setq index 0)
    (foreach primitive (ast:g-get 'primitives path nil)
      (setq stations (list 0.0 (ast:g-length primitive)))
      (foreach node connections
        (setq point (ast:g-get 'point node nil))
        (if (and (vl-some '(lambda (inc) (= (ast:g-get 'path inc nil) (ast:g-get 'id path nil))) (ast:g-get 'incidences node nil)) (ast:g-point-on primitive point))
          (setq stations (cons (ast:n-station primitive point) stations))))
      (setq sorted (vl-sort stations '<) markers nil)
      (foreach marker (ast:g-get 'landmarks path nil) (if (= index (ast:g-get 'primitive marker 0)) (setq markers (cons marker markers))))
      (while (cdr sorted)
        (setq start (car sorted) finish (cadr sorted) local-marks nil)
        (if (> (- finish start) 1e-8)
          (progn
            (foreach marker markers
              (if (and (>= (ast:g-get 'station marker 0) (- start 1e-8)) (<= (ast:g-get 'station marker 0) (+ finish 1e-8)))
                (setq local-marks (cons (list '(primitive . 0) (cons 'station (- (ast:g-get 'station marker 0) start))) local-marks))))
            (setq edges (append edges (list (list (cons 'id next-id) (cons 'path (ast:g-get 'id path nil))
              (cons 'primitive (ast:g-trim-primitive primitive start finish)) (cons 'settings (ast:g-get 'settings path nil)) (cons 'landmarks local-marks)))) next-id (1+ next-id))))
        (setq sorted (cdr sorted)))
      (setq index (1+ index)))) edges)
(defun ast:n-nodes (edges / nodes edge side point existing arm)
  (foreach edge edges
    (foreach side '(0 1)
      (setq point (ast:g-point (ast:g-get 'primitive edge nil) (if (= side 0) 0.0 (ast:g-length (ast:g-get 'primitive edge nil))))
            arm (list (cons 'edge (ast:g-get 'id edge nil)) (cons 'side side))
            existing (vl-some '(lambda (item) (if (< (ast:g-dist point (ast:g-get 'point item nil)) 1e-8) item)) nodes))
      (if existing (setq nodes (subst (ast:n-put 'arms (append (ast:g-get 'arms existing nil) (list arm)) existing) existing nodes))
        (setq nodes (append nodes (list (list (cons 'id (length nodes)) (cons 'point point) (cons 'arms (list arm))))))))) nodes)
(defun ast:n-edge (id edges) (vl-some '(lambda (item) (if (= id (ast:g-get 'id item nil)) item)) edges))
(defun ast:n-reverse-edge (edge / primitive extent markers marker)
  (setq primitive (ast:g-get 'primitive edge nil) extent (ast:g-length primitive))
  (foreach marker (ast:g-get 'landmarks edge nil) (setq markers (cons (ast:n-put 'station (- extent (ast:g-get 'station marker 0)) marker) markers)))
  (ast:n-put 'primitive (ast:g-reverse-primitive primitive) (ast:n-put 'landmarks markers edge)))
(defun ast:n-profile-same (aa bb / same key fallback)
  (setq same T)
  (foreach key '(slit-length lean handedness stitch-hand diameter thickness margin)
    (setq fallback (cond ((= key 'slit-length) 1.5) ((= key 'lean) (* pi (/ 40.0 180.0))) ((member key '(handedness stitch-hand)) 1) ((= key 'diameter) 0.5) (T nil)))
    (if (not (equal (ast:g-get key aa fallback) (ast:g-get key bb fallback) 1e-12)) (setq same nil))) same)
(defun ast:n-collapse (edges / changed nodes node arms first-arm second-arm first-edge second-edge incoming outgoing settings-a settings-b merged markers marker extent)
  (setq changed T)
  (while changed
    (setq changed nil nodes (ast:n-nodes edges))
    (foreach node nodes
      (if (and (null changed) (= (length (ast:g-get 'arms node nil)) 2))
        (progn
          (setq arms (ast:g-get 'arms node nil))
          ;; Preserve source travel when a closed phase cut is removed.
          (if (and (= (ast:g-get 'side (car arms) 0) 0) (= (ast:g-get 'side (cadr arms) 0) 1)) (setq arms (reverse arms)))
          (setq first-arm (car arms) second-arm (cadr arms)
                first-edge (ast:n-edge (ast:g-get 'edge first-arm nil) edges) second-edge (ast:n-edge (ast:g-get 'edge second-arm nil) edges))
          (if (/= (ast:g-get 'id first-edge nil) (ast:g-get 'id second-edge nil))
            (progn
              (setq incoming (if (= (ast:g-get 'side first-arm 0) 1) first-edge (ast:n-reverse-edge first-edge))
                    outgoing (if (= (ast:g-get 'side second-arm 0) 0) second-edge (ast:n-reverse-edge second-edge))
                    settings-a (ast:g-get 'settings incoming nil) settings-b (ast:g-get 'settings outgoing nil))
              (if (and (ast:g-mergeable (ast:g-get 'primitive incoming nil) (ast:g-get 'primitive outgoing nil))
                       (ast:g-near (ast:g-get 'pitch settings-a 3.0) (ast:g-get 'pitch settings-b 3.0))
                       (equal (ast:g-get 'corrections settings-a T) (ast:g-get 'corrections settings-b T)))
                (progn
                  (setq extent (ast:g-length (ast:g-get 'primitive incoming nil)) markers (ast:g-get 'landmarks incoming nil))
                  (foreach marker (ast:g-get 'landmarks outgoing nil)
                    (setq marker (ast:n-put 'station (+ extent (ast:g-get 'station marker 0)) marker))
                    (if (not (vl-some '(lambda (item) (< (abs (- (ast:g-get 'station item 0) (ast:g-get 'station marker 0))) 1e-8)) markers))
                      (setq markers (append markers (list marker)))))
                  (setq merged (ast:n-put 'primitive (ast:g-merge (ast:g-get 'primitive incoming nil) (ast:g-get 'primitive outgoing nil)) (ast:n-put 'landmarks markers incoming))
                        edges (subst merged first-edge (vl-remove second-edge edges)) changed T))))))))) edges)
(defun ast:n-set-edge (edges id key value / edge)
  (setq edge (ast:n-edge id edges)) (subst (ast:n-put key value edge) edge edges))

;;; All physical feature reservations are committed before any span is fitted.
(defun ast:n-reserve (edges / nodes result node arms arm side edge primitive settings degree kind first-arm second-arm first-edge second-edge incoming outgoing corner opening limit error virtual-slits corner-adjustments)
  (setq nodes (ast:n-nodes edges))
  (foreach edge edges
    (setq edges (ast:n-set-edge edges (ast:g-get 'id edge nil) 'start 0.0)
          edges (ast:n-set-edge edges (ast:g-get 'id edge nil) 'finish (ast:g-length (ast:g-get 'primitive edge nil)))))
  (foreach node nodes
    (setq arms (ast:g-get 'arms node nil) degree (length arms) kind 'smooth opening nil virtual-slits nil corner-adjustments nil)
    (cond
      ((> degree 2)
        (setq kind 'branch edge (ast:n-edge (ast:g-get 'edge (car arms) nil) edges)
              opening (list '(type . round) (cons 'center (ast:g-get 'point node nil)) (cons 'diameter (ast:g-get 'diameter (ast:g-get 'settings edge nil) 0.5))))
        (foreach arm arms
          (setq side (ast:g-get 'side arm 0) edge (ast:n-edge (ast:g-get 'edge arm nil) edges) primitive (ast:g-get 'primitive edge nil)
                limit (ast:g-step primitive (/ (ast:g-get 'pitch (ast:g-get 'settings edge nil) 3.0) 2.0)))
          (setq edges (ast:n-set-edge edges (ast:g-get 'id edge nil) (if (= side 0) 'start 'finish) (if (= side 0) limit (- (ast:g-length primitive) limit))))))
      ((= degree 2)
        (setq first-arm (car arms) second-arm (cadr arms) first-edge (ast:n-edge (ast:g-get 'edge first-arm nil) edges)
              second-edge (ast:n-edge (ast:g-get 'edge second-arm nil) edges)
              incoming (if (= (ast:g-get 'side first-arm 0) 1) (ast:g-get 'primitive first-edge nil) (ast:g-reverse-primitive (ast:g-get 'primitive first-edge nil)))
              outgoing (if (= (ast:g-get 'side second-arm 0) 0) (ast:g-get 'primitive second-edge nil) (ast:g-reverse-primitive (ast:g-get 'primitive second-edge nil))))
        (if (not (and (> (ast:g-dot (ast:g-tangent incoming (ast:g-length incoming)) (ast:g-tangent outgoing 0.0)) 0.0)
                      (< (abs (ast:g-cross (ast:g-tangent incoming (ast:g-length incoming)) (ast:g-tangent outgoing 0.0))) 1e-10)))
          (progn
            (setq kind 'sharp settings (ast:n-put 'incoming-pitch (ast:g-get 'pitch (ast:g-get 'settings first-edge nil) 3.0)
              (ast:n-put 'outgoing-pitch (ast:g-get 'pitch (ast:g-get 'settings second-edge nil) 3.0)
                (ast:n-put 'outgoing-corrections (ast:g-get 'corrections (ast:g-get 'settings second-edge nil) T)
                  (ast:g-get 'settings first-edge nil))))
                  corner (ast:g-corner incoming outgoing settings))
            (if (not (ast:g-get 'ok corner nil)) (setq error (ast:g-get 'error corner nil))
              (progn
                (setq opening (ast:g-get 'opening corner nil) virtual-slits (ast:g-get 'virtual-slits corner nil)
                      corner-adjustments (ast:g-get 'corner-adjustments corner nil)
                      limit (ast:g-get 'incoming-station corner 0.0) side (ast:g-get 'side first-arm 0)
                      edges (ast:n-set-edge edges (ast:g-get 'id first-edge nil) (if (= side 0) 'start 'finish) (if (= side 0) (- (ast:g-length incoming) limit) limit))
                      limit (ast:g-get 'outgoing-station corner 0.0) side (ast:g-get 'side second-arm 0)
                      edges (ast:n-set-edge edges (ast:g-get 'id second-edge nil) (if (= side 0) 'start 'finish) (if (= side 0) limit (- (ast:g-length outgoing) limit)))))))))
      (T (setq kind 'terminal)))
    (setq node (ast:n-put 'corner-adjustments corner-adjustments (ast:n-put 'virtual-slits virtual-slits
      (ast:n-put 'kind kind (ast:n-put 'opening (if opening (cons (cons 'node (ast:g-get 'id node nil)) opening)) node)))))
    (foreach arm arms (setq edges (ast:n-set-edge edges (ast:g-get 'edge arm nil) (if (= (ast:g-get 'side arm 0) 0) 'start-node 'end-node) node)))
    (setq result (append result (list node))))
  (if error (ast:g-error error) (list '(ok . T) (cons 'edges edges) (cons 'nodes result))))
(defun ast:n-append-opening (opening openings / identity existing)
  (setq identity (assoc 'node opening))
  (if (and identity (setq existing (vl-some '(lambda (item) (if (equal identity (assoc 'node item)) item)) openings)))
    (if (ast:g-same-opening opening existing) openings nil)
    (append openings (list opening))))
(defun ast:g-solve-set (paths connections / error prepared path item profile ids resolved node incidence owner point edges reservations nodes openings intervals warnings edge primitive settings start finish start-node end-node result cuts cut index local-intervals adjusted all-primitives virtual-slits corner-adjustments)
  (if (null paths) (setq error "Select a stitch line first."))
  (foreach path paths
    (if (not (and (numberp (ast:g-get 'id path nil)) (= (ast:g-get 'id path nil) (fix (ast:g-get 'id path nil)))))
      (setq error "The connected-line list is invalid. No stitches were generated."))
    (if (member (ast:g-get 'id path nil) ids) (setq error "The same stitch line appears twice in this connection. Disconnect and reconnect the affected lines."))
    (setq ids (cons (ast:g-get 'id path nil) ids))
    (if (null profile) (setq profile (list (ast:g-get 'settings path nil))))
    (if (not (ast:n-profile-same (car profile) (ast:g-get 'settings path nil))) (setq error "These lines use different hole sizes or tool settings. Use matching settings before connecting them."))
    (if (null error)
      (progn (setq item (ast:n-prepare path))
        (if (ast:g-get 'ok item nil) (setq prepared (append prepared (list item))) (setq error (ast:g-get 'error item nil))))))
  (if (null error)
    (progn (setq resolved (ast:g-resolve-connections paths connections))
      (if (ast:g-get 'ok resolved nil) (setq connections (ast:g-get 'connections resolved nil)) (setq error (ast:g-get 'error resolved nil)))))
  (foreach node connections
    (foreach incidence (ast:g-get 'incidences node nil)
      (setq owner (vl-some '(lambda (item) (if (= (ast:g-get 'id item nil) (ast:g-get 'path incidence nil)) item)) prepared)
            point (ast:g-get 'point node nil))
      (if (and (null error) (not (vl-some '(lambda (primitive) (ast:g-point-on primitive point)) (ast:g-get 'primitives owner nil))))
        (setq error "A junction lies outside the chosen start and end. Extend the stitching to include it, or disconnect that line."))))
  (if (null error) (setq error (ast:n-crossing-error prepared connections)))
  (if (null error)
    (progn
      (setq edges (ast:n-collapse (ast:n-split prepared connections)) reservations (ast:n-reserve edges))
      (if (ast:g-get 'ok reservations nil) (setq edges (ast:g-get 'edges reservations nil) nodes (ast:g-get 'nodes reservations nil)) (setq error (ast:g-get 'error reservations nil)))))
  (if (null error)
    (progn
      (foreach node nodes
        (if (ast:g-get 'opening node nil) (setq openings (append openings (list (ast:g-get 'opening node nil)))))
        (setq virtual-slits (append virtual-slits (ast:g-get 'virtual-slits node nil))
              corner-adjustments (append corner-adjustments (ast:g-get 'corner-adjustments node nil))))
      (setq index 0)
      (foreach edge edges
        (if (null error)
          (progn
            (setq primitive (ast:g-get 'primitive edge nil) settings (ast:g-get 'settings edge nil) start (ast:g-get 'start edge 0.0) finish (ast:g-get 'finish edge 0.0)
                  start-node (ast:g-get 'start-node edge nil) end-node (ast:g-get 'end-node edge nil))
            (cond
              ;; Feature reservations must remain inside each finite arm and not overlap.
              ((or (< start -1e-8) (> finish (+ (ast:g-length primitive) 1e-8)) (> start (+ finish 1e-8)))
                (setq error "Junction stitches do not fit on this section. Move the junctions farther apart or lengthen the line."))
              (T
                (setq result (ast:g-solve-primitive primitive settings (ast:g-get 'landmarks edge nil) start finish))
                (if (not (ast:g-get 'ok result nil)) (setq error (strcat "Connected line: " (ast:g-get 'error result "Stitches could not be fitted to this section.")))
                  (progn
                    (setq cuts (ast:g-get 'openings result nil) local-intervals (ast:g-get 'intervals result nil))
                    (foreach cut cuts
                      (if (and (member (ast:g-get 'kind start-node nil) '(smooth terminal)) (< (ast:g-dist (ast:g-get 'center cut nil) (ast:g-get 'point start-node nil)) 1e-8))
                        (setq cut (cons (cons 'node (ast:g-get 'id start-node nil)) cut)))
                      (if (and (member (ast:g-get 'kind end-node nil) '(smooth terminal)) (< (ast:g-dist (ast:g-get 'center cut nil) (ast:g-get 'point end-node nil)) 1e-8))
                        (setq cut (cons (cons 'node (ast:g-get 'id end-node nil)) cut)))
                      (setq item (ast:n-append-opening cut openings))
                      (if item (setq openings item) (setq error "The connected lines require different holes at the same point. Change the junction layout.")))
                    (setq intervals (append intervals (mapcar '(lambda (interval) (cons (cons 'primitive index) interval)) local-intervals)))
                    (if (ast:g-get 'opening start-node nil)
                      (setq intervals (append intervals (list (ast:g-junction-interval (ast:g-get 'center (ast:g-get 'opening start-node nil) nil) (ast:g-point primitive start) index)))))
                    (if (ast:g-get 'opening end-node nil)
                      (setq intervals (append intervals (list (ast:g-junction-interval (ast:g-point primitive finish) (ast:g-get 'center (ast:g-get 'opening end-node nil) nil) index)))))))))
            (if (> (length openings) 2000) (setq error "These connected lines need more than 2000 holes. Disconnect some lines and generate smaller groups."))))
        (setq all-primitives (append all-primitives (list (ast:g-get 'primitive edge nil))) index (1+ index)))
      (if (null error) (setq error (ast:g-validate-openings openings (car profile))))))
  (if error (ast:g-error error)
    (progn
      (setq warnings (list "The distance from stitch holes to the material edge has not been checked."))
      (if (or (null (ast:g-get 'thickness (car profile) nil)) (null (ast:g-get 'margin (car profile) nil)))
        (setq warnings (cons "Slit width and the material needed between holes have not been calibrated." warnings)))
      (if (vl-some '(lambda (item) (= (ast:g-get 'kind item nil) 'branch)) nodes)
        (setq warnings (cons "Place shared junction holes individually. Check that the hole can carry the required threads." warnings)))
      (if (vl-some '(lambda (item) (= (ast:g-get 'kind item nil) 'arc)) all-primitives)
        (setq warnings (cons "Place holes individually on curves; a multi-tooth chisel may not follow the curve." warnings)))
      (setq adjusted (or corner-adjustments (vl-some '(lambda (item) (= (ast:g-get 'kind item nil) 'corrected)) intervals)))
      (if adjusted (setq warnings (cons "Use individual placement where spacing is adjusted; a fixed-pitch chisel will not match it." warnings)))
      (list '(ok . T) (cons 'status (if adjusted 'adjusted 'exact)) (cons 'openings openings) (cons 'intervals intervals)
        (cons 'virtual-slits virtual-slits) (cons 'corner-adjustments corner-adjustments)
        (cons 'warnings warnings) (cons 'primitives all-primitives) (cons 'connections connections)))))
(princ)
