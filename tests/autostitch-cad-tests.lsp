;;; Native integration tests. Run only in a dedicated disposable test drawing.
(defun ast:cad-test-assert (condition label)
  (if condition (setq ast:*cad-test-passed* (1+ ast:*cad-test-passed*))
    (setq ast:*cad-test-failures* (cons label ast:*cad-test-failures*)))
  (princ (strcat "\n" (if condition "PASS " "FAIL ") label)))
(defun ast:cad-test-block-cuts (output / entity data count)
  (setq entity (tblobjname "BLOCK" (cdr (assoc 2 (entget output)))) count 0)
  (while (and (setq entity (entnext entity)) (/= (cdr (assoc 0 (setq data (entget entity)))) "ENDBLK"))
    (if (and (= "AUTOSTITCH" (cdr (assoc 8 data)))
             (or (= "CIRCLE" (cdr (assoc 0 data)))
                 (and (= "LINE" (cdr (assoc 0 data))) (= 30 (cdr (assoc 370 data))))))
      (setq count (1+ count)))) count)
(defun ast:cad-test-inserts (/ selection)
  (if (setq selection (ssget "_X" '((0 . "INSERT") (8 . "AUTOSTITCH")))) (sslength selection) 0))
(defun ast:cad-tests (/ ast:*cad-test-passed* ast:*cad-test-failures* original-units settings guide result output first-name before-count record data stage landmarks original-echo)
  (setq ast:*cad-test-passed* 0 ast:*cad-test-failures* nil original-units (getvar "INSUNITS") original-echo (getvar "CMDECHO"))
  (setvar "INSUNITS" 4)
  (setq settings (ast:cad-default-settings))
  (entmake '((0 . "LINE") (8 . "0") (10 0.0 0.0 0.0) (11 30.0 0.0 0.0)))
  (setq guide (entlast) before-count (ast:cad-test-inserts))
  (setq result (ast:cad-generate guide settings nil))
  (ast:cad-test-assert (ast:cad-get 'ok result) "Generate 30 mm LINE")
  (if (ast:cad-get 'ok result)
    (progn
      (setq output (ast:cad-get 'output result) first-name (cdr (assoc 2 (entget output))))
      (ast:cad-test-assert (= 11 (ast:cad-test-block-cuts output)) "Eleven real slits in generated block")
      (ast:cad-test-assert (= (1+ before-count) (ast:cad-test-inserts)) "Exactly one output reference")
      (ast:cad-test-assert (equal guide (ast:cad-get 'guide (ast:cad-read output))) "Output resolves reciprocal source")
      (ast:cad-test-assert (not (ast:cad-get 'stale (ast:cad-read guide))) "Fresh generation is current")
      (setvar "INSUNITS" 1)
      (ast:cad-test-assert (and (equal 1.0 (ast:cad-get 'factor (ast:cad-read guide)))
                              (not (ast:cad-get 'stale (ast:cad-read guide))))
        "Changing declared drawing units retains the saved seam conversion")
      (ast:cad-test-assert (equal 16.5 (ast:cad-get 'station (ast:cad-project guide '(16.5 0.0 0.0))) 1e-9)
        "New picks on an existing seam use its saved physical units")
      (setq result (ast:cad-generate guide settings nil))
      (ast:cad-test-assert (and (ast:cad-get 'ok result) (= 11 (ast:cad-test-block-cuts output))
                              (equal 1.0 (ast:cad-get 'factor (ast:cad-record guide))))
        "Regeneration after INSUNITS change preserves opening spacing and count")
      (setvar "INSUNITS" 4)
      (setq data (entget guide))
      (entmod (subst '(11 30.5 0.0 0.0) (assoc 11 data) data))
      (ast:cad-test-assert (ast:cad-get 'stale (ast:cad-read guide)) "Source edit marks output stale")
      (setq result (ast:cad-generate guide settings nil))
      (ast:cad-test-assert (and (ast:cad-get 'ok result) (equal output (ast:cad-get 'output result))
                         (= first-name (cdr (assoc 2 (entget output))))) "Regenerate preserves the output reference and stitch block name")
      (setq first-name (cdr (assoc 2 (entget output))) record (ast:cad-record guide))
      (foreach stage '("block-start" "geometry" "block-name" "guide-metadata" "output-metadata")
        (setq ast:*cad-fail-stage* stage result (ast:cad-generate guide settings nil) ast:*cad-fail-stage* nil)
        (ast:cad-test-assert (not (ast:cad-get 'ok result)) (strcat "Failure reported at " stage))
        (ast:cad-test-assert (and (equal first-name (cdr (assoc 2 (entget output))))
                                (equal record (ast:cad-record guide))
                                (= (1+ before-count) (ast:cad-test-inserts)))
                            (strcat "Failure rolls back geometry and metadata at " stage)))
      (setq data (entget output))
      (entmod (subst '(10 2.0 0.0 0.0) (assoc 10 data) data))
      (setq result (ast:cad-generate guide settings nil))
      (ast:cad-test-assert (not (ast:cad-get 'ok result)) "Moved output requires explicit repair")
      (entmod data)
      (setq landmarks '(((primitive . 0) (station . 16.5))))
      (setq data (entget guide)) (entmod (subst '(11 30.0 0.0 0.0) (assoc 11 data) data))
      (setq result (ast:cad-generate guide settings landmarks))
      (ast:cad-test-assert (ast:cad-get 'ok result) "Generate fixed-station landmark")
      (setq data (entget guide)) (entmod (subst '(11 40.0 0.0 0.0) (assoc 11 data) data))
      (ast:cad-test-assert (equal 16.5 (ast:cad-get 'station (car (ast:cad-get 'landmarks (ast:cad-read guide)))) 1e-9)
                          "Stretch retains fixed physical landmark station")
      (setq data (entget guide)) (entmod (subst '(11 12.0 0.0 0.0) (assoc 11 data) data))
      (setq first-name (cdr (assoc 2 (entget output))) result (ast:cad-generate guide settings landmarks))
      (ast:cad-test-assert (and (not (ast:cad-get 'ok result)) (equal first-name (cdr (assoc 2 (entget output)))))
                          "Shortening below landmark retains previous complete output")))
  (ast:cad-test-assert (= original-echo (getvar "CMDECHO")) "Writer restores CMDECHO")
  (setvar "INSUNITS" original-units)
  (list (cons 'passed ast:*cad-test-passed*) (cons 'failed (length ast:*cad-test-failures*))
        (cons 'failures (reverse ast:*cad-test-failures*))))
(princ)

(defun ast:cad-range-tests (/ ast:*cad-test-passed* ast:*cad-test-failures* settings guide anchor result state data rewritten count item original-units)
  (setq ast:*cad-test-passed* 0 ast:*cad-test-failures* nil original-units (getvar "INSUNITS") settings (ast:cad-default-settings))
  (setvar "INSUNITS" 4)
  (entmake '((0 . "LWPOLYLINE") (100 . "AcDbEntity") (8 . "0") (100 . "AcDbPolyline")
             (90 . 3) (70 . 0) (10 0.0 150.0) (10 30.0 150.0) (10 30.0 180.0)))
  (setq guide (entlast) anchor (ast:cad-range-anchor guide '((primitive . 1) (station . 9.0)))
        settings (ast:cad-put 'start-anchor anchor (ast:cad-put 'start 39.0 settings))
        result (ast:cad-save-inputs guide settings nil))
  (ast:cad-test-assert (ast:cad-get 'ok result) "Typed range anchor saves")
  (setq data (entget guide) rewritten nil count 0)
  (foreach item data
    (if (= 10 (car item))
      (progn (setq count (1+ count))
        (if (= count 2) (setq rewritten (append rewritten '((10 15.0 150.0)))))))
    (setq rewritten (append rewritten (list item))))
  (entmod (ast:cad-put 90 4 rewritten))
  (setq state (ast:cad-read guide))
  (ast:cad-test-assert (and (ast:cad-get 'ok state) (ast:cad-get 'range-conflict state)) "Changed topology leaves range editable but marks conflict")
  (setq result (ast:cad-generate guide settings nil))
  (ast:cad-test-assert (not (ast:cad-get 'ok result)) "Unrepaired typed range cannot silently change owning branch")
  (setq settings (ast:cad-put 'pitch 3.1 settings) result (ast:cad-save-inputs guide settings nil))
  (ast:cad-test-assert (and (ast:cad-get 'ok result) (ast:cad-get 'range-conflict (ast:cad-read guide))) "Unrelated input edit does not bless stale range snapshot")
  (setq anchor (ast:cad-range-anchor guide '((primitive . 2) (station . 9.0)))
        settings (ast:cad-put 'start-anchor anchor settings)
        result (ast:cad-save-inputs guide settings nil) state (ast:cad-read guide))
  (ast:cad-test-assert (and (ast:cad-get 'ok result) (null (ast:cad-get 'range-conflict state))
                          (equal 39.0 (ast:cad-get 'start (ast:cad-get 'settings state)) 1e-8)) "Fresh range pick repairs correspondence and recomputes global station")
  (entmake '((0 . "LINE") (8 . "0") (10 0.0 200.0 0.0) (11 30.0 200.0 0.0)))
  (setq guide (entlast) anchor (ast:cad-range-anchor guide '((primitive . 0) (station . 27.0)))
        settings (ast:cad-put 'end-anchor anchor (ast:cad-put 'end 27.0 (ast:cad-default-settings))))
  (ast:cad-save-inputs guide settings nil)
  (setq data (entget guide)) (entmod (ast:cad-put 11 '(40.0 200.0 0.0) data))
  (setq state (ast:cad-read guide))
  (ast:cad-test-assert (and (null (ast:cad-get 'range-conflict state))
                          (equal 27.0 (ast:cad-get 'end (ast:cad-get 'settings state)) 1e-8)) "Line stretch preserves explicit endpoint attachment distance")
  (entmod (ast:cad-put 11 '(20.0 200.0 0.0) (entget guide)))
  (ast:cad-test-assert (ast:cad-get 'range-conflict (ast:cad-read guide)) "Shortened line rejects out-of-range endpoint attachment")
  (entmake (list '(0 . "ARC") '(8 . "0") '(10 0.0 250.0 0.0) '(40 . 20.0) '(50 . 0.0) (cons 51 (/ pi 2))))
  (setq guide (entlast) anchor (ast:cad-range-anchor guide '((primitive . 0) (station . 6.0)))
        settings (ast:cad-put 'start-anchor anchor (ast:cad-put 'start 6.0 (ast:cad-default-settings))))
  (ast:cad-save-inputs guide settings nil)
  (entmod (ast:cad-put 40 30.0 (entget guide)))
  (setq state (ast:cad-read guide))
  (ast:cad-test-assert (and (null (ast:cad-get 'range-conflict state))
                          (equal 6.0 (ast:cad-get 'start (ast:cad-get 'settings state)) 1e-8)) "Arc radius edit preserves physical start attachment distance")
  (setvar "INSUNITS" original-units)
  (list (cons 'passed ast:*cad-test-passed*) (cons 'failed (length ast:*cad-test-failures*))
        (cons 'failures (reverse ast:*cad-test-failures*))))

(defun ast:cad-correspondence-tests (/ ast:*cad-test-passed* ast:*cad-test-failures* settings guide landmarks result data rewritten vertex-count item record original-units)
  (setq ast:*cad-test-passed* 0 ast:*cad-test-failures* nil original-units (getvar "INSUNITS")
        settings (ast:cad-default-settings) landmarks '(((primitive . 0) (station . 9.0)) ((primitive . 1) (station . 9.0))))
  (setvar "INSUNITS" 4)
  (entmake '((0 . "LWPOLYLINE") (100 . "AcDbEntity") (8 . "0") (100 . "AcDbPolyline")
             (90 . 3) (70 . 0) (10 0.0 100.0) (10 30.0 100.0) (10 30.0 130.0)))
  (setq guide (entlast) result (ast:cad-save-inputs guide settings landmarks))
  (ast:cad-test-assert (ast:cad-get 'ok result) "Correspondence fixture saves two landmarks")
  (setq data (entget guide) rewritten nil vertex-count 0)
  (foreach item data
    (if (= 10 (car item))
      (progn
        (setq vertex-count (1+ vertex-count))
        (if (= vertex-count 2) (setq rewritten (append rewritten '((10 15.0 100.0)))))))
    (setq rewritten (append rewritten (list item))))
  (entmod (ast:cad-put 90 4 rewritten))
  (setq record (ast:cad-record guide))
  (setq result (ast:cad-save-inputs guide settings (cdr landmarks)))
  (ast:cad-test-assert (and (not (ast:cad-get 'ok result)) (equal record (ast:cad-record guide)))
                       "Deleting one landmark cannot rebase another after vertex insertion")
  (setq result (ast:cad-save-inputs guide settings (cons '((primitive . 0) (station . 4.0)) (cdr landmarks))))
  (ast:cad-test-assert (and (not (ast:cad-get 'ok result)) (equal record (ast:cad-record guide)))
                       "Moving one landmark cannot rebase remaining attachments")
  (setq result (ast:cad-save-inputs guide settings nil))
  (ast:cad-test-assert (ast:cad-get 'ok result) "Clear all landmarks permits explicit correspondence repair")
  (setq result (ast:cad-save-inputs guide settings '(((primitive . 2) (station . 9.0)))))
  (ast:cad-test-assert (ast:cad-get 'ok result) "New picks attach to current topology after clear")
  (setvar "INSUNITS" original-units)
  (list (cons 'passed ast:*cad-test-passed*) (cons 'failed (length ast:*cad-test-failures*))
        (cons 'failures (reverse ast:*cad-test-failures*))))

(defun ast:cad-repair-tests (/ ast:*cad-test-passed* ast:*cad-test-failures* settings guide output result data bad-settings name record stage original-units)
  (setq ast:*cad-test-passed* 0 ast:*cad-test-failures* nil original-units (getvar "INSUNITS") settings (ast:cad-default-settings))
  (setvar "INSUNITS" 4)
  (entmake '((0 . "LINE") (8 . "0") (10 0.0 80.0 0.0) (11 30.0 80.0 0.0)))
  (setq guide (entlast) result (ast:cad-generate guide settings nil) output (ast:cad-get 'output result))
  (ast:cad-test-assert output "Repair fixture generated")
  (if output
    (progn
      (setq data (entget output))
      (entmod (ast:cad-put 41 2.0 (ast:cad-put 10 '(7.0 3.0 0.0) data)))
      (ast:cad-test-assert (ast:cad-get 'placement-conflict (ast:cad-read guide)) "Transformed output exposes repair state")
      (setq data (entget output) bad-settings (ast:cad-put 'pitch 100.0 settings)
            result (ast:cad-restore guide bad-settings nil))
      (ast:cad-test-assert (and (not (ast:cad-get 'ok result)) (equal data (entget output))) "Infeasible Restore preserves prior transformed output")
      (setq result (ast:cad-restore guide settings nil))
      (ast:cad-test-assert (and (ast:cad-get 'ok result) (ast:cad-placement-ok-p output)
                              (not (ast:cad-get 'stale (ast:cad-read guide)))) "Explicit Restore repairs output from live guide")
      (setq record (ast:cad-record guide) name (cdr (assoc 2 (entget output))))
      (foreach stage '("detach-guide" "detach-output")
        (setq ast:*cad-fail-stage* stage result (ast:cad-detach guide) ast:*cad-fail-stage* nil)
        (ast:cad-test-assert (and (not (ast:cad-get 'ok result)) (equal record (ast:cad-record guide))
                                (equal guide (ast:cad-get 'link (ast:cad-record output))))
                            (strcat "Detach failure rolls back associations at " stage)))
      (setq result (ast:cad-detach output))
      (ast:cad-test-assert (and (ast:cad-get 'ok result) (entget output)
                              (equal name (cdr (assoc 2 (entget output))))
                              (null (ast:cad-get 'link (ast:cad-record guide)))
                              (null (ast:cad-get 'link (ast:cad-record output)))) "Detach preserves cuts and clears both references")
      (setq result (ast:cad-generate guide settings nil))
      (ast:cad-test-assert (and (ast:cad-get 'ok result) (not (equal output (ast:cad-get 'output result)))
                              (entget output) (equal name (cdr (assoc 2 (entget output))))) "Generate after Detach creates independent output without deleting static cuts")
      (ast:cad-test-assert (not (ast:cad-get 'ok (ast:cad-read output))) "Detached static cuts cannot reopen a live seam")))
  (setvar "INSUNITS" original-units)
  (list (cons 'passed ast:*cad-test-passed*) (cons 'failed (length ast:*cad-test-failures*))
        (cons 'failures (reverse ast:*cad-test-failures*))))

(defun ast:cad-lifecycle-tests (/ ast:*cad-test-passed* ast:*cad-test-failures* settings guide output result data original-name copy-guide copy-output layer-data block-entity original-units inches-guide inches-output cut-data)
  (setq ast:*cad-test-passed* 0 ast:*cad-test-failures* nil original-units (getvar "INSUNITS") settings (ast:cad-default-settings))
  (setvar "INSUNITS" 4)
  (entmake '((0 . "LINE") (8 . "0") (10 0.0 50.0 0.0) (11 30.0 50.0 0.0)))
  (setq guide (entlast) result (ast:cad-generate guide settings nil) output (ast:cad-get 'output result))
  (ast:cad-test-assert (ast:cad-get 'ok result) "Lifecycle fixture generated")
  (if output
    (progn
      (setq data (entget guide))
      (entmod (subst '(11 40.0 60.0 0.0) (assoc 11 data) (subst '(10 10.0 60.0 0.0) (assoc 10 data) data)))
      (setq data (entget output)) (entmod (subst '(10 10.0 10.0 0.0) (assoc 10 data) data))
      (setq result (ast:cad-read guide))
      (ast:cad-test-assert (and (ast:cad-get 'common-placement result) (not (ast:cad-get 'stale result))) "Common translation remains current")
      (setq result (ast:cad-generate guide settings nil))
      (ast:cad-test-assert (and (ast:cad-get 'ok result) (ast:cad-placement-ok-p output)) "Generate after common move restores canonical output placement")
      (setq data (entget guide))
      (entmod (subst '(11 -60.0 40.0 0.0) (assoc 11 data) (subst '(10 -60.0 10.0 0.0) (assoc 10 data) data)))
      (setq data (entget output)) (entmod (subst (cons 50 (/ pi 2)) (assoc 50 data) data))
      (setq result (ast:cad-read guide))
      (ast:cad-test-assert (and (ast:cad-get 'common-placement result) (not (ast:cad-get 'stale result))) "Common quarter-turn remains current")
      (ast:cad-generate guide settings nil)
      (setq original-name (cdr (assoc 2 (entget output)))
            copy-output (vlax-vla-object->ename (vla-Copy (vlax-ename->vla-object output))))
      (ast:cad-test-assert (not (ast:cad-get 'ok (ast:cad-read copy-output))) "Output-only copy is static and cannot edit original")
      (setq copy-guide (vlax-vla-object->ename (vla-Copy (vlax-ename->vla-object guide))))
      (ast:cad-test-assert (null (ast:cad-get 'output (ast:cad-read copy-guide))) "Guide-only copy cannot inherit original output")
      (setq result (ast:cad-generate copy-guide settings nil))
      (ast:cad-test-assert (and (ast:cad-get 'ok result) (not (equal output (ast:cad-get 'output result)))
                              (equal original-name (cdr (assoc 2 (entget output))))) "Copied guide creates independent output")
      (ast:cad-test-assert (equal original-name (cdr (assoc 2 (entget copy-output)))) "Static copied output retains shared original definition")
      (setq data (entget output)) (entmod (subst '(41 . 2.0) (assoc 41 data) data))
      (ast:cad-test-assert (not (ast:cad-get 'ok (ast:cad-generate guide settings nil))) "Scaled output cannot silently change physical pitch")
      (entmod data)
      (setq layer-data (entget (tblobjname "LAYER" "AUTOSTITCH")))
      (entmod (subst (cons 70 (logior 4 (cdr (assoc 70 layer-data)))) (assoc 70 layer-data) layer-data))
      (ast:cad-test-assert (not (ast:cad-get 'ok (ast:cad-generate guide settings nil))) "Locked output layer rejects write")
      (entmod layer-data)
      (setq block-entity (entnext (tblobjname "BLOCK" (cdr (assoc 2 (entget output))))) data (entget block-entity))
      (entmod (subst (cons 10 (mapcar '+ (cdr (assoc 10 data)) '(0.25 0.0 0.0))) (assoc 10 data) data))
      (ast:cad-test-assert (ast:cad-get 'stale (ast:cad-read guide)) "Manual cut alteration is detected")
      (setq result (ast:cad-generate guide settings nil))
      (ast:cad-test-assert (and (ast:cad-get 'ok result) (not (ast:cad-get 'stale (ast:cad-read guide)))) "Explicit Generate replaces altered block content")))
  (setvar "INSUNITS" 1)
  (entmake (list '(0 . "LINE") '(8 . "0") '(10 0.0 5.0 0.0) (cons 11 (list (/ 30.0 25.4) 5.0 0.0))))
  (setq inches-guide (entlast) result (ast:cad-generate inches-guide settings nil) inches-output (ast:cad-get 'output result))
  (ast:cad-test-assert (and (ast:cad-get 'ok result) (= 11 (ast:cad-get 'count result))) "Inch guide solves in physical millimetres")
  (if inches-output
    (progn
      (setq cut-data (entget (entnext (tblobjname "BLOCK" (cdr (assoc 2 (entget inches-output)))))))
      (ast:cad-test-assert (equal (* 25.4 (distance (cdr (assoc 10 cut-data)) (cdr (assoc 11 cut-data)))) 1.5 1e-8)
                           "Inch output slit retains 1.5 mm physical length")))
  (setvar "INSUNITS" original-units)
  (list (cons 'passed ast:*cad-test-passed*) (cons 'failed (length ast:*cad-test-failures*))
        (cons 'failures (reverse ast:*cad-test-failures*))))


(defun ast:cad-identity-tests (/ ast:*cad-test-passed* ast:*cad-test-failures* original-units settings guide output result identity copy-output signature copy-guide counter record name blocks)
  (setq ast:*cad-test-passed* 0 ast:*cad-test-failures* nil original-units (getvar "INSUNITS")
        settings (ast:cad-default-settings))
  (setvar "INSUNITS" 4)
  (setq guide (entmakex '((0 . "LINE") (8 . "0") (10 0.0 1900.0 0.0) (11 30.0 1900.0 0.0)))
        counter (dictsearch (namedobjdict) "AUTOSTITCH_IDS_V1")
        ast:*cad-fail-stage* "block-name" result (ast:cad-generate guide settings nil) ast:*cad-fail-stage* nil)
  (ast:cad-test-assert (and (not (ast:cad-get 'ok result)) (null (ast:cad-record guide))
    (equal counter (dictsearch (namedobjdict) "AUTOSTITCH_IDS_V1")))
    "Failed first generation rolls back its ID reservation and metadata")
  (setq result (ast:cad-generate guide settings nil) output (ast:cad-get 'output result)
        identity (ast:cad-stitch-id guide))
  (ast:cad-test-assert (and (ast:cad-id-number identity) (= identity (cdr (assoc 2 (entget output)))))
    "Generated stitch ID and block name are the same ST-number")
  (vl-cmdf "_.UNDO" "1")
  (ast:cad-test-assert (and (null (ast:cad-record guide))
    (equal counter (dictsearch (namedobjdict) "AUTOSTITCH_IDS_V1")))
    "Undo generation removes the ID and restores the drawing counter")
  (vl-cmdf "_.REDO")
  (ast:cad-test-assert (and (= identity (ast:cad-stitch-id guide))
    (= identity (cdr (assoc 2 (entget output))))) "Redo restores the same stitch ID and block name")
  (setq copy-output (vlax-vla-object->ename (vla-Copy (vlax-ename->vla-object output)))
        signature (ast:cad-output-signature copy-output))
  (entmod (ast:cad-put 11 '(33.0 1900.0 0.0) (entget guide)))
  (setq result (ast:cad-generate guide settings nil))
  (ast:cad-test-assert (and (ast:cad-get 'ok result) (= identity (ast:cad-stitch-id guide))
    (= identity (cdr (assoc 2 (entget output)))) (equal signature (ast:cad-output-signature copy-output))
    (not (equal signature (ast:cad-output-signature output))))
    "Regeneration keeps ST-number while a static output copy keeps its original geometry")
  (setq copy-guide (vlax-vla-object->ename (vla-Copy (vlax-ename->vla-object guide))))
  (ast:cad-test-assert (= "" (ast:cad-stitch-id copy-guide)) "An unassigned copied guide does not display its original stitch ID")
  (setq result (ast:cad-generate copy-guide settings nil))
  (ast:cad-test-assert (and (ast:cad-get 'ok result)
    (= (1+ (ast:cad-id-number identity)) (ast:cad-id-number (ast:cad-stitch-id copy-guide)))
    (= (ast:cad-stitch-id copy-guide) (cdr (assoc 2 (entget (ast:cad-get 'output result))))))
    "Copied guide receives the next stitch number and a matching independent block")
  (vl-cmdf "_.ERASE" guide "")
  (vl-cmdf "_.UNDO" "1")
  (ast:cad-test-assert (= identity (ast:cad-stitch-id guide)) "Undo deletion restores the original stitch ID")
  ;; Simulate a saved pre-ID drawing without changing its geometry or reciprocal links.
  (setq record (vl-remove-if '(lambda (item) (member (car item) '(stitch-id stitch-owner link))) (ast:cad-record guide)))
  (ast:cad-write-record guide record output)
  (setq record (vl-remove-if '(lambda (item) (member (car item) '(stitch-id output-identity link))) (ast:cad-record output)))
  (ast:cad-write-record output record guide)
  (setq blocks (vla-get-Blocks (vla-get-ActiveDocument (vlax-get-acad-object)))
        name (strcat "AUTOSTITCH_" (cdr (assoc 5 (entget guide))) "_R99"))
  (vla-put-Name (vla-Item blocks identity) name)
  (setq result (ast:cad-transaction 'ast:cad-ensure-stitch-id (list guide)) identity (ast:cad-stitch-id guide))
  (ast:cad-test-assert (and (ast:cad-id-number identity) (= name (cdr (assoc 2 (entget output)))))
    "Legacy label migration assigns ST-number without regenerating existing output")
  (setq result (ast:cad-generate guide settings nil))
  (ast:cad-test-assert (and (ast:cad-get 'ok result) (= identity (cdr (assoc 2 (entget output))))
    (= identity (ast:cad-stitch-id guide))) "Legacy output adopts its assigned ST-number on generation")
  (vla-put-Name (vla-Item blocks identity) (strcat "RENAMED_" identity))
  (entmake (list '(0 . "BLOCK") (cons 2 identity) '(70 . 0) '(10 0.0 0.0 0.0)))
  (entmake '((0 . "POINT") (8 . "0") (10 12.0 34.0 0.0)))
  (entmake '((0 . "ENDBLK")))
  (setq record (tblsearch "BLOCK" identity) result (ast:cad-generate guide settings nil))
  (ast:cad-test-assert (and (ast:cad-get 'ok result) (/= identity (ast:cad-stitch-id guide))
    (= (ast:cad-stitch-id guide) (cdr (assoc 2 (entget output))))
    (equal record (tblsearch "BLOCK" identity)))
    "A foreign block claiming a renamed output ID is preserved and the stitch receives a free ID")
  (setvar "INSUNITS" original-units)
  (list (cons 'passed ast:*cad-test-passed*) (cons 'failed (length ast:*cad-test-failures*))
    (cons 'failures (reverse ast:*cad-test-failures*))))
