;;; Connected-path integration checks. Root runs these in a disposable drawing.
(defun ast:cad-test-junction-upgrade (guide / state output record signature result)
  (setq state (ast:cad-read guide) output (ast:cad-get 'output state)
        record (ast:cad-record output) signature (ast:cad-output-signature output))
  (ast:cad-write-record output (vl-remove-if '(lambda (item) (member (car item) '(link junction-version))) record)
    (ast:cad-get 'link record))
  (ast:cad-test-assert (and (ast:cad-get 'stale (ast:cad-read guide))
    (equal signature (ast:cad-output-signature output)))
    "Connected output predating the half-pitch rule is marked stale without changing its geometry")
  (setq ast:*cad-fail-stage* "set-output-metadata"
        result (ast:cad-generate guide (ast:cad-get 'settings state) (ast:cad-get 'landmarks state)) ast:*cad-fail-stage* nil)
  (ast:cad-test-assert (and (not (ast:cad-get 'ok result)) (ast:cad-get 'stale (ast:cad-read guide))
    (null (ast:cad-get 'junction-version (ast:cad-record output)))
    (equal signature (ast:cad-output-signature output)))
    "Failed junction migration retains the prior output and its regeneration requirement")
  (setq result (ast:cad-generate guide (ast:cad-get 'settings state) (ast:cad-get 'landmarks state)))
  (ast:cad-test-assert (and (ast:cad-get 'ok result) (not (ast:cad-get 'stale (ast:cad-read guide)))
    (= 1 (ast:cad-get 'junction-version (ast:cad-record output))))
    "Successful regeneration records the half-pitch junction rule and clears stale output"))

(defun ast:cad-connected-tests (/ ast:*cad-test-passed* ast:*cad-test-failures* original-units original-copy settings first second third first-output second-output result state first-record second-record first-name count stage data copy member-settings unrelated unrelated-output selection before cursor copied-guide copied-output preview)
  (setq ast:*cad-test-passed* 0 ast:*cad-test-failures* nil original-units (getvar "INSUNITS")
        original-copy (getvar "COPYMODE") settings (ast:cad-default-settings))
  (setvar "INSUNITS" 4)
  (entmake '((0 . "LINE") (8 . "0") (10 -13.5 500.0 0.0) (11 13.5 500.0 0.0)))
  (setq first (entlast) result (ast:cad-generate first settings nil) first-output (ast:cad-get 'output result))
  (entmake '((0 . "LINE") (8 . "0") (10 0.0 500.0 0.0) (11 0.0 513.5 0.0)))
  (setq second (entlast) result (ast:cad-generate second settings nil) second-output (ast:cad-get 'output result))
  (entmake '((0 . "LINE") (8 . "0") (10 50.0 500.0 0.0) (11 80.0 500.0 0.0)))
  (setq unrelated (entlast) result (ast:cad-generate unrelated settings nil) unrelated-output (ast:cad-get 'output result)
        count (ast:cad-test-inserts) first-record (ast:cad-record first) second-record (ast:cad-record second)
        first-name (cdr (assoc 2 (entget first-output))))
  (setq ast:*cad-fail-stage* "retired-output"
        result (ast:cad-connect first second '(0.0 500.0 0.0) settings nil) ast:*cad-fail-stage* nil)
  (ast:cad-test-assert (not (ast:cad-get 'ok result)) "Connect reports failure while retiring old output")
  (ast:cad-test-assert (and (entget first-output) (entget second-output)
                          (equal first-record (ast:cad-record first)) (equal second-record (ast:cad-record second))
                          (= count (ast:cad-test-inserts)) (equal first-name (cdr (assoc 2 (entget first-output)))))
                       "Failed Connect restores both independent sources and outputs")
  (setq result (ast:cad-connect first second '(0.0 500.0 0.0) settings nil))
  (ast:cad-test-assert (ast:cad-get 'ok result) "Connect two independent LINEs into a T")
  (if (ast:cad-get 'ok result)
    (progn
      (ast:cad-test-assert (and (equal first-output (ast:cad-get 'output result)) (null (entget second-output))
                              (= (1- count) (ast:cad-test-inserts))) "T has one shared output and retires duplicate references")
      (ast:cad-test-assert (= 16 (ast:cad-test-block-cuts first-output)) "T emits fifteen slits and one shared hole")
      (ast:cad-test-assert (and (equal first (ast:cad-get 'guide (ast:cad-read first-output)))
                              (equal second (ast:cad-get 'guide (ast:cad-read second)))
                              (= 2 (length (ast:cad-get 'members (ast:cad-read second)))))
                           "Either source opens its own inputs; output opens the shared job")
      (setq member-settings (ast:cad-put 'pitch 4.0 settings)
            result (ast:cad-generate second member-settings nil))
      (ast:cad-test-assert (and (ast:cad-get 'ok result)
                              (= 3.0 (ast:cad-get 'pitch (ast:cad-get 'settings (ast:cad-read first))))
                              (= 4.0 (ast:cad-get 'pitch (ast:cad-get 'settings (ast:cad-read second)))))
                           "Member pitch stays independent while shared output regenerates")
      (setq result (ast:cad-generate second settings nil))
      (ast:cad-test-junction-upgrade second)
      (setq data (entget first)) (entmod (ast:cad-put 11 '(16.5 500.0 0.0) data))
      (ast:cad-test-assert (ast:cad-get 'stale (ast:cad-read second)) "Editing one source marks the whole connected set stale")
      (setq result (ast:cad-generate second settings nil))
      (ast:cad-test-assert (and (ast:cad-get 'ok result) (= 17 (ast:cad-test-block-cuts first-output)))
                           "Generate from the other source updates the edited through-path")
      (setq first-record (ast:cad-record first) second-record (ast:cad-record second)
            first-name (cdr (assoc 2 (entget first-output))) count (ast:cad-test-inserts))
      (foreach stage '("member-metadata-0" "member-metadata-1" "set-output-metadata")
        (setq ast:*cad-fail-stage* stage result (ast:cad-generate second settings nil) ast:*cad-fail-stage* nil)
        (ast:cad-test-assert (and (not (ast:cad-get 'ok result))
                                (equal first-record (ast:cad-record first)) (equal second-record (ast:cad-record second))
                                (equal first-name (cdr (assoc 2 (entget first-output)))) (= count (ast:cad-test-inserts)))
                             (strcat "Connected replacement rolls back at " stage)))
      (setq data (entget second)) (entmod (ast:cad-put 11 '(0.0 502.0 0.0) data))
      (setq result (ast:cad-generate first settings nil))
      (ast:cad-test-assert (and (not (ast:cad-get 'ok result)) (equal first-name (cdr (assoc 2 (entget first-output)))))
                           "An insufficient arm preserves the complete connected output")
      (entmod data)
      (setq copy (vlax-vla-object->ename (vla-Copy (vlax-ename->vla-object second))) state (ast:cad-read copy))
      (ast:cad-test-assert (and (ast:cad-get 'ok state) (= 1 (length (ast:cad-get 'members state)))
                              (null (ast:cad-get 'output state)) (equal first-record (ast:cad-record first)))
                           "Copied member starts independent and cannot edit original output")
      (setq ast:*cad-fail-stage* "disconnected-component" result (ast:cad-disconnect second) ast:*cad-fail-stage* nil)
      (ast:cad-test-assert (and (not (ast:cad-get 'ok result))
                              (= 2 (length (ast:cad-get 'members (ast:cad-read second))))
                              (equal first-name (cdr (assoc 2 (entget first-output)))))
                           "Failed Disconnect rolls back every component")
      (setq result (ast:cad-disconnect second))
      (ast:cad-test-assert (and (ast:cad-get 'ok result)
                              (= 1 (length (ast:cad-get 'members (ast:cad-read first))))
                              (= 1 (length (ast:cad-get 'members (ast:cad-read second))))
                              (not (equal (ast:cad-get 'output (ast:cad-read first))
                                          (ast:cad-get 'output (ast:cad-read second)))))
                           "Disconnect creates independently editable outputs")
      (ast:cad-test-assert (and (= first-name (ast:cad-stitch-id first))
        (/= (ast:cad-stitch-id first) (ast:cad-stitch-id second))
        (= (ast:cad-stitch-id second) (cdr (assoc 2 (entget (ast:cad-get 'output (ast:cad-read second)))))))
        "Disconnect retains the first component ID and gives the other component a new ID")
      (ast:cad-test-assert (and (equal unrelated-output (ast:cad-get 'output (ast:cad-read unrelated)))
                              (not (ast:cad-get 'stale (ast:cad-read unrelated))))
                           "Unrelated path and output remain current and unchanged")))
  (entmake '((0 . "LINE") (8 . "0") (10 -13.5 560.0 0.0) (11 13.5 560.0 0.0)))
  (setq first (entlast))
  (entmake '((0 . "LINE") (8 . "0") (10 0.0 546.5 0.0) (11 0.0 573.5 0.0)))
  (setq second (entlast) result (ast:cad-connect first second '(0.0 560.0 0.0) settings nil))
  (ast:cad-test-assert (and (ast:cad-get 'ok result) (= 21 (ast:cad-test-block-cuts (ast:cad-get 'output result))))
                       "X crossing emits twenty slits and exactly one shared hole")
  (if (ast:cad-get 'ok result)
    (progn
      (setq first-output (ast:cad-get 'output result) first-name (cdr (assoc 2 (entget first-output)))
            selection (ssadd first) copied-guide nil copied-output nil)
      (ssadd second selection) (ssadd first-output selection)
      (setvar "COPYMODE" 1)
      (setq before (entlast))
      (vl-cmdf "_.COPY" selection "" "_non" '(0.0 0.0 0.0) "_non" '(60.0 0.0 0.0))
      (setq cursor (entnext before))
      (while cursor
        (cond ((= "LINE" (cdr (assoc 0 (entget cursor)))) (setq copied-guide cursor))
              ((and (= "INSERT" (cdr (assoc 0 (entget cursor))))
                    (= "AUTOSTITCH" (cdr (assoc 8 (entget cursor))))) (setq copied-output cursor)))
        (setq cursor (entnext cursor)))
      (setq state (ast:cad-read copied-guide))
      (ast:cad-test-assert (and (ast:cad-get 'ok state) (= 2 (length (ast:cad-get 'members state)))
                              (equal copied-output (ast:cad-get 'output state))
                              (ast:cad-get 'common-placement state) (not (ast:cad-get 'stale state)))
                           "Native complete-set COPY remaps all member and output references")
      (setq result (ast:cad-generate copied-guide settings nil))
      (ast:cad-test-assert (and (ast:cad-get 'ok result)
                              (equal first-name (cdr (assoc 2 (entget first-output))))
                              (/= first-name (cdr (assoc 2 (entget copied-output)))))
                           "Complete connected copy regenerates without changing original cuts")
      (ast:cad-test-assert (and (= (ast:cad-stitch-id first) (ast:cad-stitch-id second))
        (/= (ast:cad-stitch-id first) (ast:cad-stitch-id copied-guide))
        (= (ast:cad-stitch-id copied-guide) (cdr (assoc 2 (entget copied-output)))))
        "Connected members share one ST-number and a complete copied set receives another")
      (setq copy (vlax-vla-object->ename (vla-Copy (vlax-ename->vla-object first))) state (ast:cad-read copy))
      (ast:cad-test-assert (and (ast:cad-get 'ok state) (= 1 (length (ast:cad-get 'members state)))
                              (null (ast:cad-get 'output state)))
                           "Primary-only copy does not retain uncopied original members")
      (setq copy (vlax-vla-object->ename (vla-Copy (vlax-ename->vla-object first-output))))
      (ast:cad-test-assert (not (ast:cad-get 'ok (ast:cad-read copy)))
                           "Connected output-only copy cannot reopen original work")))
  (entmake '((0 . "LINE") (8 . "0") (10 -14.5 650.0 0.0) (11 14.5 650.0 0.0)))
  (setq first (entlast))
  (entmake '((0 . "CIRCLE") (8 . "0") (10 0.0 650.0 0.0) (40 . 10.0)))
  (setq second (entlast) preview (ast:cad-connect-preview first second))
  (ast:cad-test-assert (and (ast:cad-get 'ok preview) (= 2 (ast:cad-get 'count preview)))
                       "Connect preview reports both line-circle intersections")
  (setq result (ast:cad-connect first second nil settings nil))
  (ast:cad-test-assert (and (ast:cad-get 'ok result)
                          (= 2 (length (ast:cad-get 'connections (ast:cad-read first)))))
                       "Connect All coordinates both circle intersections atomically")
  (if (ast:cad-get 'ok result)
    (ast:cad-test-assert (= 0 (ast:cad-get 'count (ast:cad-connect-preview first second)))
                         "Connect preview excludes already declared intersections"))
  (entmake '((0 . "LINE") (8 . "0") (10 -24.0 700.0 0.0) (11 24.0 700.0 0.0)))
  (setq first (entlast))
  (entmake '((0 . "LINE") (8 . "0") (10 0.0 700.0 0.0) (11 0.0 724.0 0.0)))
  (setq second (entlast) result (ast:cad-connect first second nil settings nil))
  (entmake '((0 . "LINE") (8 . "0") (10 24.0 700.0 0.0) (11 0.0 724.0 0.0)))
  (setq third (entlast) preview (ast:cad-connect-preview first third))
  (ast:cad-test-assert (and (ast:cad-get 'ok preview) (= 2 (ast:cad-get 'count preview)))
                       "Connect preview counts crossings with every existing member")
  (setq result (ast:cad-connect first third nil settings nil))
  (ast:cad-test-assert (and (ast:cad-get 'ok result)
                          (= 3 (length (ast:cad-get 'members (ast:cad-read third))))
                          (= 3 (length (ast:cad-get 'connections (ast:cad-read third)))))
                       "Connect All merges a third path across both existing members")
  (setvar "INSUNITS" original-units)
  (setvar "COPYMODE" original-copy)
  (list (cons 'passed ast:*cad-test-passed*) (cons 'failed (length ast:*cad-test-failures*))
        (cons 'failures (reverse ast:*cad-test-failures*))))
(princ)

(defun ast:cad-missing-tests (/ ast:*cad-test-passed* ast:*cad-test-failures* original-units settings first second third output result state name record copy helper)
  (setq ast:*cad-test-passed* 0 ast:*cad-test-failures* nil original-units (getvar "INSUNITS")
        settings (ast:cad-default-settings))
  (setvar "INSUNITS" 4)
  (entmake '((0 . "LINE") (8 . "0") (10 -13.5 900.0 0.0) (11 19.5 900.0 0.0)))
  (setq first (entlast))
  (entmake '((0 . "LINE") (8 . "0") (10 0.0 900.0 0.0) (11 0.0 913.5 0.0)))
  (setq second (entlast) result (ast:cad-connect first second nil settings nil))
  (entmake '((0 . "LINE") (8 . "0") (10 6.0 900.0 0.0) (11 6.0 886.5 0.0)))
  (setq third (entlast) result (ast:cad-connect first third nil settings nil) output (ast:cad-get 'output result))
  (ast:cad-test-assert (ast:cad-get 'ok result) "Three-line missing-member fixture connects")
  (if output
    (progn
      (setq name (cdr (assoc 2 (entget output))) record (ast:cad-record output))
      (ast:cad-test-assert (and (= 3 (length (ast:cad-get 'members record)))
          (null (assoc 'source-route (car (ast:cad-get 'incidences (car (ast:cad-get 'connections record)))))))
        "Output backs up native membership and connection topology without source geometry")
      (entdel second)
      (setq state (ast:cad-read third))
      (ast:cad-test-assert (and (ast:cad-get 'ok state) (ast:cad-get 'missing-members state)
          (ast:cad-get 'connection-conflict state) (ast:cad-get 'stale state) (equal output (ast:cad-get 'output state)))
        "Deleted member leaves surviving line editable with explicit repair state")
      (setq result (ast:cad-generate third settings nil))
      (ast:cad-test-assert (and (not (ast:cad-get 'ok result)) (equal name (cdr (assoc 2 (entget output)))))
        "Generate preserves previous complete output until missing member repair")
      (setq ast:*cad-fail-stage* "member-metadata-1" result (ast:cad-disconnect third) ast:*cad-fail-stage* nil)
      (ast:cad-test-assert (and (not (ast:cad-get 'ok result)) (null (entget second))
          (equal name (cdr (assoc 2 (entget output)))) (equal record (ast:cad-record output))
          (ast:cad-get 'missing-members (ast:cad-read third)))
        "Failed missing-member repair restores output and retains earlier source deletion")
      (setq result (ast:cad-disconnect output) state (ast:cad-read third))
      (ast:cad-test-assert (and (ast:cad-get 'ok result) (not (ast:cad-get 'missing-members state))
          (= 2 (length (ast:cad-get 'members state))) (= 1 (length (ast:cad-get 'connections state))))
        "Explicit repair removes missing incidences while preserving surviving connections")
      (setq name (cdr (assoc 2 (entget output))))
      (if (member 'ast:markers-reference (atoms-family 0)) (setq helper (ast:markers-reference first)))
      (entdel first)
      (setq state (ast:cad-read output))
      (ast:cad-test-assert (and (ast:cad-get 'ok state) (equal third (ast:cad-get 'guide state))
          (ast:cad-get 'missing-members state) (equal output (ast:cad-get 'output state)))
        "Output reopens a surviving line after its primary source was deleted")
      (setq copy (vlax-vla-object->ename (vla-Copy (vlax-ename->vla-object output))))
      (ast:cad-test-assert (not (ast:cad-get 'ok (ast:cad-read copy)))
        "Copied orphaned output cannot borrow surviving original sources")
      (setq copy (vlax-vla-object->ename (vla-Copy (vlax-ename->vla-object third))) state (ast:cad-read copy))
      (ast:cad-test-assert (and (ast:cad-get 'ok state) (= 1 (length (ast:cad-get 'members state)))
          (null (ast:cad-get 'output state))) "Copied surviving source cannot repair the original missing-primary group")
      (setq ast:*cad-fail-stage* "geometry" result (ast:cad-disconnect third) ast:*cad-fail-stage* nil)
      (ast:cad-test-assert (and (not (ast:cad-get 'ok result)) (null (entget first))
          (equal name (cdr (assoc 2 (entget output))))) "Failed primary recovery preserves cuts and source deletion")
      (if (and helper (member 'ast:markers-prune-missing (atoms-family 0)))
        (progn
          (setq ast:*cad-fail-stage* "missing-markers" result (ast:cad-disconnect third) ast:*cad-fail-stage* nil)
          (ast:cad-test-assert (and (not (ast:cad-get 'ok result)) (entget helper) (null (entget first))
              (equal name (cdr (assoc 2 (entget output)))))
            "Failed repair after orphan marker pruning restores helpers and complete output")))
      (setq result (ast:cad-disconnect output) state (ast:cad-read third))
      (ast:cad-test-assert (and (ast:cad-get 'ok result) (not (ast:cad-get 'missing-members state))
          (= 1 (length (ast:cad-get 'members state))) (= 6 (ast:cad-test-block-cuts output))
          (equal third (ast:cad-get 'guide (ast:cad-read output))))
        "Primary recovery reuses output for the remaining canonical source")))
  (setvar "INSUNITS" original-units)
  (list (cons 'passed ast:*cad-test-passed*) (cons 'failed (length ast:*cad-test-failures*))
        (cons 'failures (reverse ast:*cad-test-failures*))))

(defun ast:cad-missing-reopen-fixture (/ settings first second result output)
  (setq settings (ast:cad-default-settings))
  (entmake '((0 . "LINE") (8 . "0") (10 -13.5 980.0 0.0) (11 13.5 980.0 0.0)))
  (setq first (entlast))
  (entmake '((0 . "LINE") (8 . "0") (10 0.0 980.0 0.0) (11 0.0 993.5 0.0)))
  (setq second (entlast) result (ast:cad-connect first second nil settings nil) output (ast:cad-get 'output result))
  (if output (entdel first))
  (list (cons 'ok (ast:cad-get 'ok result)) (cons 'source second) (cons 'output output)
        (cons 'source-handle (cdr (assoc 5 (entget second))))
        (cons 'output-handle (if output (cdr (assoc 5 (entget output)))))))

;;; Run fixture before saving the disposable drawing; run checks after reopening it.
(defun ast:cad-pending-reopen-fixture (data-path / original-units settings missing y first second first-output second-output result fixtures error stream)
  (setq original-units (getvar "INSUNITS") settings (ast:cad-default-settings))
  (setvar "INSUNITS" 4)
  (foreach missing '(nil T)
    (if (null error)
      (progn
        (setq y (if missing 2520.0 2450.0)
              first (entmakex (list '(0 . "LINE") '(8 . "0") (cons 10 (list 0.0 y 0.0)) (cons 11 (list 30.0 y 0.0))))
              second (entmakex (list '(0 . "LINE") '(8 . "0") (cons 10 (list 30.0 y 0.0)) (cons 11 (list 30.0 (+ y 30.0) 0.0))))
              result (ast:cad-generate first settings nil) first-output (ast:cad-get 'output result))
        (if (not (ast:cad-get 'ok result)) (setq error (ast:cad-get 'error result)))
        (if (null error)
          (progn
            (setq result (ast:cad-generate second settings nil) second-output (ast:cad-get 'output result))
            (if (not (ast:cad-get 'ok result)) (setq error (ast:cad-get 'error result)))))
        (if (null error)
          (progn
            (setq result (ast:cad-connect-guides first second nil settings nil))
            (if (not (ast:cad-get 'ok result)) (setq error (ast:cad-get 'error result)))))
        (if (null error)
          (progn
            (setq fixtures (append fixtures (list (list (cons 'missing-primary missing)
              (cons 'first (cdr (assoc 5 (entget first)))) (cons 'second (cdr (assoc 5 (entget second))))
              (cons 'first-output (cdr (assoc 5 (entget first-output))))
              (cons 'second-output (cdr (assoc 5 (entget second-output))))
              (cons 'stitch-id (ast:cad-stitch-id first))))))
            (if missing (entdel first)))))))
  (setvar "INSUNITS" original-units)
  (if (null error)
    (if (setq stream (open data-path "w"))
      (progn (prin1 fixtures stream) (close stream))
      (setq error "Could not write the pending-guide fixture handles.")))
  (if error (list '(ok . nil) (cons 'error error))
    (list '(ok . T) (cons 'data-path data-path) (cons 'fixtures fixtures))))

(defun ast:cad-pending-reopen-tests (data-path / ast:*cad-test-passed* ast:*cad-test-failures* stream fixtures fixture missing first second first-output second-output state members result identity label)
  (setq ast:*cad-test-passed* 0 ast:*cad-test-failures* nil stream (open data-path "r"))
  (if stream (progn (setq fixtures (read (read-line stream))) (close stream)))
  (ast:cad-test-assert (= 2 (length fixtures)) "Pending reopen fixture contains both saved scenarios")
  (foreach fixture fixtures
    (setq missing (ast:cad-get 'missing-primary fixture)
          label (if missing "Deleted primary: " "Intact group: ")
          first (handent (ast:cad-get 'first fixture)) second (handent (ast:cad-get 'second fixture))
          first-output (handent (ast:cad-get 'first-output fixture)) second-output (handent (ast:cad-get 'second-output fixture))
          identity (ast:cad-get 'stitch-id fixture) state (ast:cad-read second) members (ast:cad-get 'members state))
    (ast:cad-test-assert (and (ast:cad-get 'ok state) (= 2 (length members))
      (ast:cad-get 'stale state) (ast:cad-get 'topology-pending (ast:cad-record second))
      (if missing (and (or (null first) (null (entget first))) (ast:cad-get 'missing-members state))
        (and (member first members) (not (ast:cad-get 'missing-members state)))))
      (strcat label "pending membership and deletion state survive save/reopen"))
    (ast:cad-test-assert (and first-output second-output (entget first-output) (entget second-output)
      (member first-output (ast:cad-get 'retained-outputs (ast:cad-record second)))
      (member second-output (ast:cad-get 'retained-outputs (ast:cad-record second)))
      (member (ast:cad-get 'guide (ast:cad-read first-output)) members)
      (member (ast:cad-get 'guide (ast:cad-read second-output)) members))
      (strcat label "both retained outputs remain owned and selectable after reopen"))
    (setq result (ast:cad-transaction 'ast:cad-ensure-stitch-id (list second)))
    (ast:cad-test-assert (and (eq (type result) 'STR) (= identity result) (= identity (ast:cad-stitch-id second)))
      (strcat label "selecting the reopened guide preserves its stitch ID"))
    (if missing
      (progn
        (setq result (ast:cad-disconnect-guides second))
        (ast:cad-test-assert (and (ast:cad-get 'ok result)
          (= 1 (length (ast:cad-get 'members (ast:cad-read second))))
          (equal second (ast:cad-get 'guide (ast:cad-read first-output)))
          (equal second (ast:cad-get 'guide (ast:cad-read second-output))))
          "Deleted primary: repair preserves access to both previous outputs")))
    (setq result (ast:cad-generate second (ast:cad-default-settings) nil) state (ast:cad-read second))
    (ast:cad-test-assert (and (ast:cad-get 'ok result) (equal first-output (ast:cad-get 'output result))
      second-output (null (entget second-output)))
      (strcat label "Generate reuses the canonical output and retires the superseded output"))
    (ast:cad-test-assert (and (ast:cad-get 'ok state) (not (ast:cad-get 'stale state))
      (not (ast:cad-get 'topology-pending (ast:cad-record second)))
      (= identity (ast:cad-stitch-id second)) (= (if missing 1 2) (length (ast:cad-get 'members state))))
      (strcat label "generated ownership and stitch ID are current after reopen")))
  (list (cons 'passed ast:*cad-test-passed*) (cons 'failed (length ast:*cad-test-failures*))
    (cons 'failures (reverse ast:*cad-test-failures*))))

(defun ast:cad-guide-workflow-tests (/ ast:*cad-test-passed* ast:*cad-test-failures* original-units original-copy settings first second result state count first-output second-output first-data second-data first-record second-record output signature first-id second-id selection before cursor copies)
  (setq ast:*cad-test-passed* 0 ast:*cad-test-failures* nil original-units (getvar "INSUNITS")
        original-copy (getvar "COPYMODE") settings (ast:cad-default-settings))
  (setvar "INSUNITS" 4)
  (setq first (entmakex '((0 . "LINE") (8 . "0") (10 -15.0 2100.0 0.0) (11 0.0 2100.0 0.0)))
        second (entmakex '((0 . "LINE") (8 . "0") (10 0.0 2100.0 0.0) (11 0.0 2115.0 0.0)))
        count (ast:cad-test-inserts)
        result (ast:cad-connect-guides first second nil settings nil)
        state (ast:cad-read second))
  (ast:cad-test-assert (and (ast:cad-get 'ok result) (= count (ast:cad-test-inserts))
    (= 2 (length (ast:cad-get 'members state))) (null (ast:cad-get 'output state))
    (ast:cad-get 'stale state) (equal (ast:cad-stitch-id first) (ast:cad-stitch-id second)))
    "Connect guides persists one stitch identity without generating output")
  (vl-cmdf "_.UNDO" 1)
  (ast:cad-test-assert (and (= 1 (length (ast:cad-get 'members (ast:cad-read first))))
    (= 1 (length (ast:cad-get 'members (ast:cad-read second)))))
    "One Undo removes the ungenerated guide connection")
  (vl-cmdf "_.REDO")
  (ast:cad-test-assert (and (= 2 (length (ast:cad-get 'members (ast:cad-read second))))
    (= count (ast:cad-test-inserts))) "Redo restores guide topology without generating stitches")
  (setq result (ast:cad-generate second settings nil) output (ast:cad-get 'output result))
  (ast:cad-test-assert (and (ast:cad-get 'ok result) output (= (1+ count) (ast:cad-test-inserts))
    (not (ast:cad-get 'stale (ast:cad-read first))) (not (ast:cad-get 'stale (ast:cad-read second))))
    "Generate after connecting unstitched guides creates one current shared output")
  (setq signature (ast:cad-output-signature output) count (ast:cad-test-inserts)
        result (ast:cad-disconnect-guides second))
  (ast:cad-test-assert (and (ast:cad-get 'ok result) (= count (ast:cad-test-inserts))
    (equal signature (ast:cad-output-signature output))
    (= 1 (length (ast:cad-get 'members (ast:cad-read second))))
    (/= (ast:cad-stitch-id first) (ast:cad-stitch-id second)))
    "Disconnect guides saves separate identities and preserves the previous shared geometry")
  (setq result (ast:cad-generate second settings nil) second-output (ast:cad-get 'output result))
  (ast:cad-test-assert (and (ast:cad-get 'ok result) (not (equal output second-output))
    (equal signature (ast:cad-output-signature output)))
    "Generating the disconnected second component leaves retained first-component output untouched")
  (setq second-data (entget second-output) result (ast:cad-generate first settings nil))
  (ast:cad-test-assert (and (ast:cad-get 'ok result) (equal second-data (entget second-output))
    (equal output (ast:cad-get 'output result)))
    "Generating the owning component preserves the independently generated component")
  ;; A new topology can be saved even when its first corner has no feasible stitch solution.
  (setq first (entmakex '((0 . "LINE") (8 . "0") (10 0.0 2150.0 0.0) (11 15.0 2150.0 0.0)))
        second (entmakex '((0 . "LINE") (8 . "0") (10 15.0 2150.0 0.0) (11 30.0 2150.01 0.0)))
        result (ast:cad-generate first settings nil) first-output (ast:cad-get 'output result)
        result (ast:cad-generate second settings nil) second-output (ast:cad-get 'output result)
        first-data (entget first-output) second-data (entget second-output)
        result (ast:cad-connect-guides first second nil settings nil))
  (ast:cad-test-assert (and (ast:cad-get 'ok result) (equal first-data (entget first-output))
    (equal second-data (entget second-output))
    (= 2 (length (ast:cad-get 'members (ast:cad-read second-output)))))
    "Connect guides preserves independent existing output and keeps it selectable")
  (setq first-record (ast:cad-record first) second-record (ast:cad-record second)
        result (ast:cad-generate second settings nil))
  (ast:cad-test-assert (and (not (ast:cad-get 'ok result))
    (equal first-data (entget first-output)) (equal second-data (entget second-output))
    (equal first-record (ast:cad-record first)) (equal second-record (ast:cad-record second)))
    "An infeasible Generate preserves pending topology and both previous stitch outputs")
  (setq result (ast:cad-disconnect-guides second))
  (ast:cad-test-assert (and (ast:cad-get 'ok result)
    (equal first-output (ast:cad-get 'output (ast:cad-read first)))
    (equal second-output (ast:cad-get 'output (ast:cad-read second))))
    "Disconnecting pending guides retains each independently owned previous output")
  ;; Pending membership on every member survives deletion of an ungenerated primary.
  (setq first (entmakex '((0 . "LINE") (8 . "0") (10 0.0 2200.0 0.0) (11 15.0 2200.0 0.0)))
        second (entmakex '((0 . "LINE") (8 . "0") (10 15.0 2200.0 0.0) (11 15.0 2215.0 0.0)))
        result (ast:cad-connect-guides first second nil settings nil))
  (entdel first)
  (setq state (ast:cad-read second))
  (ast:cad-test-assert (and (ast:cad-get 'ok state) (ast:cad-get 'missing-members state))
    "An ungenerated set reports a deleted primary from surviving guide metadata")
  (setq count (ast:cad-test-inserts) result (ast:cad-disconnect-guides second))
  (ast:cad-test-assert (and (ast:cad-get 'ok result) (= count (ast:cad-test-inserts))
    (not (ast:cad-get 'missing-members (ast:cad-read second))))
    "Removing a missing guide repairs pending topology without generating output")
  (setq first (entmakex '((0 . "LINE") (8 . "0") (10 0.0 2250.0 0.0) (11 30.0 2250.0 0.0)))
        second (entmakex '((0 . "LINE") (8 . "0") (10 30.0 2250.0 0.0) (11 30.0 2280.0 0.0)))
        result (ast:cad-generate first settings nil) first-output (ast:cad-get 'output result)
        result (ast:cad-generate second settings nil) second-output (ast:cad-get 'output result)
        result (ast:cad-connect-guides first second nil settings nil)
        first-id (ast:cad-stitch-id first))
  (entdel first)
  (ast:cad-test-assert (equal second (ast:cad-get 'guide (ast:cad-read first-output)))
    "A retained output remains selectable after its pending primary guide is deleted")
  (setq result (ast:cad-transaction 'ast:cad-ensure-stitch-id (list second)))
  (ast:cad-test-assert (= first-id (ast:cad-stitch-id second))
    "Selecting a surviving pending member keeps the shared stitch ID")
  (setq result (ast:cad-disconnect-guides second))
  (ast:cad-test-assert (and (ast:cad-get 'ok result)
    (equal second (ast:cad-get 'guide (ast:cad-read first-output))))
    "Retained output stays selectable after pending missing-guide repair")
  (setq result (ast:cad-generate second settings nil))
  (ast:cad-test-assert (and (ast:cad-get 'ok result) (equal first-output (ast:cad-get 'output result))
    (null (entget second-output)) (= first-id (ast:cad-stitch-id second)))
    "Generate after pending primary deletion reuses the shared ID and retires every superseded output")
  (setq first (entmakex '((0 . "LINE") (8 . "0") (10 0.0 2300.0 0.0) (11 30.0 2300.0 0.0)))
        second (entmakex '((0 . "LINE") (8 . "0") (10 30.0 2300.0 0.0) (11 30.0 2330.0 0.0)))
        result (ast:cad-generate first settings nil) first-output (ast:cad-get 'output result)
        result (ast:cad-generate second settings nil) second-output (ast:cad-get 'output result)
        result (ast:cad-connect-guides first second nil settings nil)
        first-data (entget first-output) second-data (entget second-output)
        first-record (ast:cad-record first) second-record (ast:cad-record second)
        selection (ssadd first (ssadd second)) before (entlast) copies nil)
  (setvar "COPYMODE" 1)
  (vl-cmdf "_.COPY" selection "" "_non" '(0.0 0.0 0.0) "_non" '(80.0 0.0 0.0))
  (setq cursor before)
  (while (setq cursor (entnext cursor))
    (if (= "LINE" (cdr (assoc 0 (entget cursor)))) (setq copies (append copies (list cursor)))))
  (setq state (ast:cad-read (car copies)) result (ast:cad-generate (car copies) settings nil))
  (ast:cad-test-assert (and (= 2 (length (ast:cad-get 'members state))) (ast:cad-get 'ok result)
    (equal first-data (entget first-output)) (equal second-data (entget second-output))
    (equal first-record (ast:cad-record first)) (equal second-record (ast:cad-record second)))
    "Copied pending guides generate independently without acquiring or retiring original outputs")
  (setq selection (ssadd first (ssadd second (ssadd first-output (ssadd second-output))))
        before (entlast) copies nil)
  (vl-cmdf "_.COPY" selection "" "_non" '(0.0 0.0 0.0) "_non" '(160.0 0.0 0.0))
  (setq cursor before)
  (while (setq cursor (entnext cursor))
    (if (= "LINE" (cdr (assoc 0 (entget cursor)))) (setq copies (append copies (list cursor)))))
  (setq state (ast:cad-read (car copies)) result (ast:cad-generate (car copies) settings nil))
  (ast:cad-test-assert (and (= 2 (length (ast:cad-get 'members state))) (ast:cad-get 'ok result)
    (equal first-data (entget first-output)) (equal second-data (entget second-output))
    (equal first-record (ast:cad-record first)) (equal second-record (ast:cad-record second))
    (/= (ast:cad-stitch-id first) (ast:cad-stitch-id (car copies))))
    "Copying pending guides with their old outputs remaps ownership and preserves the original set")
  (setq first (entmakex '((0 . "LINE") (8 . "0") (10 0.0 2370.0 0.0) (11 30.0 2370.0 0.0)))
        second (entmakex '((0 . "LINE") (8 . "0") (10 30.0 2370.0 0.0) (11 30.0 2400.0 0.0)))
        result (ast:cad-generate first settings nil) first-output (ast:cad-get 'output result)
        result (ast:cad-generate second settings nil) second-output (ast:cad-get 'output result)
        first-data (ast:cad-record first-output) second-data (ast:cad-record second-output)
        first-record (ast:cad-record first) second-record (ast:cad-record second)
        ast:*cad-fail-stage* "guide-set-metadata-1"
        result (ast:cad-connect-guides first second nil settings nil) ast:*cad-fail-stage* nil)
  (ast:cad-test-assert (and (not (ast:cad-get 'ok result))
    (equal first-data (ast:cad-record first-output)) (equal second-data (ast:cad-record second-output))
    (equal first-record (ast:cad-record first)) (equal second-record (ast:cad-record second)))
    "Failed guide connection restores both source records and both previous output records")
  (setvar "INSUNITS" original-units)
  (setvar "COPYMODE" original-copy)
  (list (cons 'passed ast:*cad-test-passed*) (cons 'failed (length ast:*cad-test-failures*))
    (cons 'failures (reverse ast:*cad-test-failures*))))
