;;; Display integration checks; run only in a disposable native drawing.
(defun ast:display-test-entities (output layer kind / entity data result)
  (if (and output (entget output))
    (progn
      (setq entity (tblobjname "BLOCK" (cdr (assoc 2 (entget output)))))
      (while (and (setq entity (entnext entity))
                  (/= "ENDBLK" (cdr (assoc 0 (setq data (entget entity))))))
        (if (and (or (null layer) (= layer (cdr (assoc 8 data))))
                 (or (null kind) (= kind (cdr (assoc 0 data)))))
          (setq result (cons data result))))))
  (reverse result))
(defun ast:display-test-openings (output kind)
  (vl-remove-if-not '(lambda (item)
    (or (= "CIRCLE" (cdr (assoc 0 item)))
      (and (= "LINE" (cdr (assoc 0 item))) (= 30 (cdr (assoc 370 item))))))
    (ast:display-test-entities output "AUTOSTITCH" kind)))
(defun ast:display-test-crossbar-entities (output)
  (vl-remove-if-not '(lambda (item) (= 0 (cdr (assoc 70 item))))
    (ast:display-test-entities output "AUTOSTITCH" "LWPOLYLINE")))
(defun ast:display-test-dashes (output)
  (vl-remove-if-not '(lambda (item) (= 9 (cdr (assoc 370 item))))
    (ast:display-test-entities output "AUTOSTITCH" "LINE")))
(defun ast:display-test-xy (point) (list (car point) (cadr point)))
(defun ast:display-test-spacing-labels (output expected factor / labels)
  (setq labels (ast:display-test-entities output "AUTOSTITCH_UI" "TEXT"))
  (and (= (length expected) (length labels))
    (vl-every '(lambda (record)
      (vl-some '(lambda (data)
        (and (= (car record) (cdr (assoc 1 data)))
          (equal (cadr record) (ast:display-test-xy (cdr (assoc 11 data))) 1e-8)
          (equal (cos (caddr record)) (cos (cdr (assoc 50 data))) 1e-8)
          (equal (sin (caddr record)) (sin (cdr (assoc 50 data))) 1e-8)
          (equal (/ 0.30 factor) (cdr (assoc 40 data)) 1e-8)
          (= 1 (cdr (assoc 72 data))) (= 2 (cdr (assoc 73 data)))
          (= 9 (cdr (assoc 370 data))))) labels)) expected)))
(defun ast:display-test-centre (data)
  (if (= "CIRCLE" (cdr (assoc 0 data))) (ast:display-test-xy (cdr (assoc 10 data)))
    (mapcar '(lambda (aa bb) (/ (+ aa bb) 2.0))
      (ast:display-test-xy (cdr (assoc 10 data))) (ast:display-test-xy (cdr (assoc 11 data))))))
(defun ast:display-test-thread-pair (threads first second)
  (vl-some '(lambda (data)
    (or (and (equal first (ast:display-test-xy (cdr (assoc 10 data))) 1e-8)
             (equal second (ast:display-test-xy (cdr (assoc 11 data))) 1e-8))
        (and (equal second (ast:display-test-xy (cdr (assoc 10 data))) 1e-8)
             (equal first (ast:display-test-xy (cdr (assoc 11 data))) 1e-8)))) threads))
(defun ast:display-test-chain (output closed / holes threads first second valid tail)
  (setq holes (ast:display-test-openings output nil)
        threads (ast:display-test-entities output "AUTOSTITCH_STITCHES" "LINE")
        valid (= (length threads) (- (length holes) (if closed 0 1))) tail holes)
  (while (and valid tail (or (cdr tail) closed))
    (setq first (car tail) second (if (cdr tail) (cadr tail) (car holes)))
    (setq valid (ast:display-test-thread-pair threads
      (ast:display-test-xy (cdr (assoc (if (= "CIRCLE" (cdr (assoc 0 first))) 10 11) first)))
      (ast:display-test-xy (cdr (assoc 10 second)))))
    (setq tail (cdr tail))) valid)
(defun ast:display-test-tip (point tangent sign / angle)
  (setq angle (+ tangent (* pi (/ 40.0 180.0))))
  (list (+ (car point) (* sign 0.75 (cos angle)))
        (+ (cadr point) (* sign 0.75 (sin angle)))))
(defun ast:display-test-polyline-vertices (data)
  (mapcar 'cdr (vl-remove-if-not '(lambda (item) (= 10 (car item))) data)))
(defun ast:display-test-crossbars (output centres factor / holes notes targets valid data centre tip vertices apex target axis first second forward-one forward-two side-one side-two)
  (setq holes (ast:display-test-openings output "LINE")
        notes (ast:display-test-crossbar-entities output) valid T)
  (foreach data holes
    (setq centre (ast:display-test-centre data))
    (if (vl-some '(lambda (point) (equal point centre 1e-8)) centres)
      (foreach tip (list (ast:display-test-xy (cdr (assoc 10 data))) (ast:display-test-xy (cdr (assoc 11 data))))
        (setq targets (cons (list tip centre) targets)))))
  (if (/= (length notes) (length targets)) (setq valid nil))
  (foreach data notes
    (setq vertices (ast:display-test-polyline-vertices data)
          apex (mapcar '(lambda (aa bb) (/ (+ aa bb) 2.0)) (car vertices) (cadr vertices))
          target (vl-some '(lambda (item) (if (equal apex (car item) 1e-8) item)) targets))
    (if (not (and (= "LWPOLYLINE" (cdr (assoc 0 data))) (= 2 (length vertices)) target
                  (equal 0 (cdr (assoc 70 data)))
                  (equal 7 (cdr (assoc 62 data))) (equal 0.0 (cdr (assoc 43 data)) 1e-8)
                  (equal 30 (cdr (assoc 370 data)))))
      (setq valid nil)
      (progn
        (setq axis (mapcar '(lambda (value) (/ value (distance apex (cadr target)))) (mapcar '- apex (cadr target)))
              first (mapcar '- (car vertices) apex) second (mapcar '- (cadr vertices) apex)
              forward-one (* factor (apply '+ (mapcar '* first axis)))
              forward-two (* factor (apply '+ (mapcar '* second axis)))
              side-one (* factor (- (* (car axis) (cadr first)) (* (cadr axis) (car first))))
              side-two (* factor (- (* (car axis) (cadr second)) (* (cadr axis) (car second)))))
        (if (not (and (equal forward-one 0.0 1e-8) (equal forward-two 0.0 1e-8)
                      (> (abs side-one) 0.15) (< (abs side-one) 0.35)
                      (equal side-one (- side-two) 1e-8))) (setq valid nil))
        (setq targets (vl-remove target targets)))))
  (and valid (null targets)))
(defun ast:display-test-visible (name / data)
  (setq data (entget (tblobjname "LAYER" name)))
  (and (> (cdr (assoc 62 data)) 0) (= 0 (logand 1 (cdr (assoc 70 data))))
       (equal 1 (cdr (assoc 290 data)))))
(defun ast:display-test-round-fills (output factor / holes fills targets data vertices centre hole radius width bulges valid)
  (setq holes (ast:display-test-entities output "AUTOSTITCH" "CIRCLE") targets holes
        fills (vl-remove-if-not '(lambda (item) (and (equal 2 (cdr (assoc 90 item))) (equal 1 (cdr (assoc 70 item)))))
                (ast:display-test-entities output "AUTOSTITCH" "LWPOLYLINE"))
        valid (= (length holes) (length fills)))
  (foreach data fills
    (setq vertices (ast:display-test-polyline-vertices data)
          centre (mapcar '(lambda (aa bb) (/ (+ aa bb) 2.0)) (car vertices) (cadr vertices))
          hole (vl-some '(lambda (item) (if (equal centre (ast:display-test-xy (cdr (assoc 10 item))) 1e-8) item)) targets)
          width (cdr (assoc 43 data)) bulges (mapcar 'cdr (vl-remove-if-not '(lambda (item) (= 42 (car item))) data)))
    (if (not (and hole (= 2 (length vertices)) (equal 1 (cdr (assoc 70 data)))
                  (equal 7 (cdr (assoc 62 data))) (equal 0 (cdr (assoc 370 data)))
                  (equal '(1.0 1.0) bulges 1e-8) (numberp width)))
      (setq valid nil)
      (progn
        (setq radius (cdr (assoc 40 hole)))
        (if (not (and (equal (* factor radius) 0.25 1e-8)
                      (equal (+ (distance centre (car vertices)) (/ width 2.0)) radius 1e-8)
                      (equal (- (distance centre (car vertices)) (/ width 2.0)) 0.0 1e-8)
                      (equal (distance centre (car vertices)) (distance centre (cadr vertices)) 1e-8))) (setq valid nil))
        (setq targets (vl-remove hole targets)))))
  (and valid (null targets)))
(defun ast:display-test-construction (output virtuals factor / dashes valid slit centre axis slit-length first last selected total data points point delta projection cross starts finishes)
  (setq dashes (ast:display-test-dashes output)
        valid (= (length dashes) (* 4 (length virtuals))))
  (foreach slit virtuals
    (setq centre (cdr (assoc 'center slit)) axis (cdr (assoc 'axis slit)) slit-length (cdr (assoc 'length slit))
          first (mapcar '- centre (mapcar '(lambda (value) (* value 0.5 slit-length)) axis))
          last (mapcar '+ centre (mapcar '(lambda (value) (* value 0.5 slit-length)) axis))
          selected nil total 0.0 starts nil finishes nil)
    (foreach data dashes
      (setq points (list
        (mapcar '(lambda (value) (* value factor)) (ast:display-test-xy (cdr (assoc 10 data))))
        (mapcar '(lambda (value) (* value factor)) (ast:display-test-xy (cdr (assoc 11 data))))))
      (if (vl-every '(lambda (point)
        (setq delta (mapcar '- point first) projection (apply '+ (mapcar '* delta axis))
              cross (- (* (car delta) (cadr axis)) (* (cadr delta) (car axis))))
        (and (< (abs cross) 1e-8) (>= projection -1e-8) (<= projection (+ slit-length 1e-8)))) points)
        (progn
          (setq selected (cons data selected) total (+ total (distance (car points) (cadr points)))
                starts (or starts (vl-some '(lambda (point) (equal point first 1e-8)) points))
                finishes (or finishes (vl-some '(lambda (point) (equal point last 1e-8)) points)))
          (if (not (and (equal 9 (cdr (assoc 370 data))) (equal 7 (cdr (assoc 62 data))))) (setq valid nil)))))
    (if (not (and (= 4 (length selected)) starts finishes (> total 0.0) (< total (* 0.8 slit-length)))) (setq valid nil))
    (foreach data selected (setq dashes (vl-remove data dashes))))
  (and valid (null dashes)))
(defun ast:display-test-t-threads (threads / valid pair first second)
  (setq valid (= 12 (length threads)))
  (foreach pair '((-10.5 -7.5) (-7.5 -4.5) (-4.5 -1.5) (-1.5 0.0)
                  (0.0 1.5) (1.5 4.5) (4.5 7.5) (7.5 10.5))
    (setq first (list (car pair) 1400.0) second (list (cadr pair) 1400.0))
    (if (not (ast:display-test-thread-pair threads
               (if (= (car pair) 0.0) first (ast:display-test-tip first 0.0 1.0))
               (if (= (cadr pair) 0.0) second (ast:display-test-tip second 0.0 -1.0)))) (setq valid nil)))
  (foreach pair '((0.0 1.5) (1.5 4.5) (4.5 7.5) (7.5 10.5))
    (setq first (list 0.0 (+ 1400.0 (car pair))) second (list 0.0 (+ 1400.0 (cadr pair))))
    (if (not (ast:display-test-thread-pair threads
               (if (= (car pair) 0.0) first (ast:display-test-tip first (/ pi 2.0) 1.0))
               (ast:display-test-tip second (/ pi 2.0) -1.0))) (setq valid nil))) valid)

(defun ast:display-tests (/ ast:*cad-test-passed* ast:*cad-test-failures* original-units original-fill original-lineweight original-dimzin settings guide result output holes threads notes data original-data signature name record first second angle centre axis valid corner-x before-x after-y tail chord changed expected stations marked layer state solution virtuals expected-virtuals virtual-in virtual-out hole fills dashes primitives corner curved-settings labels label-midpoint label-angle label-anchor)
  (setq ast:*cad-test-passed* 0 ast:*cad-test-failures* nil original-units (getvar "INSUNITS")
        original-fill (getvar "FILLMODE") original-lineweight (getvar "LWDISPLAY")
        settings (ast:cad-default-settings))
  (setvar "INSUNITS" 4)
  (entmake '((0 . "LINE") (8 . "0") (10 0.0 1100.0 0.0) (11 30.5 1100.0 0.0)))
  (setq guide (entlast) result (ast:cad-generate guide settings nil) output (ast:cad-get 'output result))
  (ast:cad-test-assert (ast:cad-get 'ok result) "Adjusted straight line generates with visual aids")
  (if output
    (progn
      (setq holes (ast:display-test-openings output "LINE")
            threads (ast:display-test-entities output "AUTOSTITCH_STITCHES" "LINE")
            notes (ast:display-test-entities output "AUTOSTITCH" "LWPOLYLINE"))
      (ast:cad-test-assert (and (= 11 (length holes)) (= 10 (length threads))) "Visual thread does not add physical openings")
      (ast:cad-test-assert (ast:display-test-chain output nil) "Straight thread joins actual selected slit tips, not hole centres")
      (ast:cad-test-assert (and (= 6 (length notes)) (ast:display-test-crossbars output
                                 '((12.0 1100.0) (15.25 1100.0) (18.5 1100.0)) 1.0))
                          "Both tips of all three affected slits have one monochrome crossbar; shared slit is not duplicated")
      (ast:cad-test-assert (not (vl-some '(lambda (item) (not (member (cdr (assoc 62 item)) '(nil 256 7)))) holes))
                          "Adjusted and nominal physical slits all retain monochrome color")
      (ast:cad-test-assert (and (null (ast:display-test-entities output "AUTOSTITCH" "TEXT"))
                              (= 6 (length (ast:display-test-crossbar-entities output))))
                          "Spacing notation contains only compact crossbars, with no text or bracket")
      (ast:cad-test-assert (and
        (ast:display-test-spacing-labels output '(("3.25" (13.625 1100.0) 0.0) ("3.25" (16.875 1100.0) 0.0)) 1.0)
        (= 0 (cdr (assoc 290 (entget (tblobjname "LAYER" "AUTOSTITCH_UI"))))))
        "Adjusted straight gaps show small upright millimetre values only on the nonprinting UI layer")
      (ast:cad-test-assert (and
        (vl-every 'ast:display-test-visible '("AUTOSTITCH_STITCHES" "AUTOSTITCH"))
        (= 1 (getvar "FILLMODE")) (= 1 (getvar "LWDISPLAY")))
        "Thread, spacing marks and construction are visible and printable without display options")
      (ast:cad-test-assert (and
        (vl-every '(lambda (item) (equal 30 (cdr (assoc 370 item)))) holes)
        (vl-every '(lambda (item) (equal 9 (cdr (assoc 370 item)))) threads))
        "Slit strokes are 0.30 mm and thread strokes remain light at 0.09 mm")
      (foreach layer '("AUTOSTITCH_STITCHES" "AUTOSTITCH")
        (setq data (entget (tblobjname "LAYER" layer)))
        (entmod (ast:cad-put 70 (logior 1 (cdr (assoc 70 data)))
          (ast:cad-put 62 (- (abs (cdr (assoc 62 data)))) (ast:cad-put 290 0 data)))))
      (setq result (ast:cad-generate guide settings nil))
      (ast:cad-test-assert (and (ast:cad-get 'ok result)
        (vl-every 'ast:display-test-visible '("AUTOSTITCH_STITCHES" "AUTOSTITCH"))
        (= 11 (ast:cad-test-block-cuts output)) (not (ast:cad-get 'stale (ast:cad-read guide))))
        "Generate restores legacy off/frozen/nonplotting display layers without adding physical holes")
      (setq signature (ast:cad-output-signature output) name (cdr (assoc 2 (entget output)))
            holes (ast:display-test-openings output "LINE")
            notes (ast:display-test-entities output "AUTOSTITCH" "LWPOLYLINE"))
      (setq labels (ast:display-test-entities output "AUTOSTITCH_UI" "TEXT"))
      (if labels
        (progn
          (setq original-data (car labels)) (entmod (ast:cad-put 1 "9.99" original-data))
          (ast:cad-test-assert (ast:cad-get 'stale (ast:cad-read guide)) "Edited adjusted-spacing value is detected by the output signature")
          (entmod original-data)))
      (if notes
        (progn
          (setq original-data (car notes))
          (entmod (subst (cons 10 (mapcar '+ (cdr (assoc 10 original-data)) '(0.1 0.0)))
                        (assoc 10 original-data) original-data))
          (ast:cad-test-assert (ast:cad-get 'stale (ast:cad-read guide)) "Edited crossbar endpoint is detected by output signature")
          (entmod original-data)
          (entmod (ast:cad-put 43 0.2 original-data))
          (ast:cad-test-assert (ast:cad-get 'stale (ast:cad-read guide)) "Edited crossbar width is detected by output signature")
          (entmod original-data)))
      (if holes
        (progn
          (setq original-data (car holes)) (entmod (ast:cad-put 62 1 original-data))
          (ast:cad-test-assert (ast:cad-get 'stale (ast:cad-read guide)) "Changed slit color is detected by output signature")
          (entmod (ast:cad-put 62 (if (assoc 62 original-data) (cdr (assoc 62 original-data)) 256) original-data))))
      (ast:cad-test-assert (not (ast:cad-get 'stale (ast:cad-read guide))) "Restoring annotations and color restores current output")
      (setq record (ast:cad-record guide) ast:*cad-fail-stage* "geometry"
            result (ast:cad-generate guide settings nil) ast:*cad-fail-stage* nil)
      (ast:cad-test-assert (and (not (ast:cad-get 'ok result)) (equal name (cdr (assoc 2 (entget output))))
                              (equal signature (ast:cad-output-signature output)) (equal record (ast:cad-record guide)))
                          "Failed annotated replacement restores prior holes, threads, notes and metadata")
      (setq ast:*cad-fail-stage* "display" result (ast:cad-generate guide settings nil) ast:*cad-fail-stage* nil)
      (ast:cad-test-assert (and (not (ast:cad-get 'ok result)) (equal name (cdr (assoc 2 (entget output))))
                              (equal signature (ast:cad-output-signature output)) (equal record (ast:cad-record guide)))
                          "Failure before ENDBLK restores prior output and metadata")
      (setq record (ast:cad-put 'display-version 4
                     (vl-remove-if '(lambda (item) (= (car item) 'link)) (ast:cad-record output))))
      (if (not (tblsearch "LAYER" "AUTOSTITCH_NOTES"))
        (entmake '((0 . "LAYER") (100 . "AcDbSymbolTableRecord")
          (100 . "AcDbLayerTableRecord") (2 . "AUTOSTITCH_NOTES") (70 . 0) (62 . 7))))
      (foreach data (ast:display-test-crossbar-entities output)
        (entmod (ast:cad-put 8 "AUTOSTITCH_NOTES" data)))
      (ast:cad-write-record output record guide)
      (ast:cad-test-assert (ast:cad-get 'stale (ast:cad-read guide)) "Previous separate-layer output version requires Generate")
      (setq result (ast:cad-generate guide settings nil))
      (ast:cad-test-assert (and (ast:cad-get 'ok result) (equal 8 (ast:cad-get 'display-version (ast:cad-record output)))
                              (not (ast:cad-get 'stale (ast:cad-read guide)))
                              (null (ast:display-test-entities output "AUTOSTITCH_NOTES" nil))
                              (= 6 (length (ast:display-test-crossbar-entities output))))
                          "Generate upgrades legacy display metadata and restores current output")))
  (entmake '((0 . "LINE") (8 . "0") (10 50.0 1100.0 0.0) (11 80.0 1100.0 0.0)))
  (setq guide (entlast) result (ast:cad-generate guide settings nil) output (ast:cad-get 'output result))
  (ast:cad-test-assert (and (ast:cad-get 'ok result) (= 11 (ast:cad-test-block-cuts output))
                          (= 10 (length (ast:display-test-entities output "AUTOSTITCH_STITCHES" "LINE"))))
                      "Exact straight run retains eleven holes and ten thread segments")
  (ast:cad-test-assert (and (null (ast:display-test-crossbar-entities output))
                          (null (ast:display-test-entities output "AUTOSTITCH_UI" "TEXT"))
                          (not (vl-some '(lambda (item) (not (member (cdr (assoc 62 item)) '(nil 256 7))))
                              (ast:display-test-openings output "LINE"))))
                      "Nominal run has no correction notes and keeps every slit ByLayer")
  (entmake (list '(0 . "ARC") '(8 . "0") '(10 0.0 1200.0 0.0) '(40 . 10.0) '(50 . 0.0) (cons 51 (/ pi 2.0))))
  (setq guide (entlast) result (ast:cad-generate guide settings nil) output (ast:cad-get 'output result)
        holes (ast:display-test-openings output "LINE") valid T)
  (foreach data holes
    (setq centre (ast:display-test-centre data) angle (atan (- (cadr centre) 1200.0) (car centre))
          axis (mapcar '- (ast:display-test-xy (cdr (assoc 11 data))) (ast:display-test-xy (cdr (assoc 10 data)))))
    (if (or (not (equal (distance centre '(0.0 1200.0)) 10.0 1e-8))
            (not (equal axis (list (* 1.5 (cos (+ angle (/ pi 2.0) (* pi (/ 40.0 180.0)))))
                                  (* 1.5 (sin (+ angle (/ pi 2.0) (* pi (/ 40.0 180.0)))))) 1e-8))) (setq valid nil)))
  (ast:cad-test-assert (and (ast:cad-get 'ok result) holes valid (ast:display-test-chain output nil))
                      "Arc thread joins tangent-oriented finite slits without changing circle geometry")
  (ast:cad-test-assert (= 8 (length (ast:display-test-entities output "AUTOSTITCH" "LWPOLYLINE")))
                      "Three equal arc corrections mark four physical slits with eight crossbars")
  ;; The nominal angular advance is 2 asin(3/20). Three equal corrected
  ;; advances occupy the remaining quarter arc; identify their actual bounding slits.
  (setq expected (* 20.0 (sin (/ (- (/ pi 2.0) (* 4.0 (atan 3.0 (sqrt 391.0)))) 6.0)))
        tail holes changed 0 valid T marked nil labels nil)
  (while (cdr tail)
    (setq chord (distance (ast:display-test-centre (car tail)) (ast:display-test-centre (cadr tail))))
    (if (not (equal chord 3.0 1e-8))
      (progn
        (setq changed (1+ changed))
        (if (not (equal chord expected 1e-8)) (setq valid nil))
        (setq first (ast:display-test-centre (car tail)) second (ast:display-test-centre (cadr tail))
              label-midpoint (mapcar '(lambda (aa bb) (/ (+ aa bb) 2.0)) first second)
              label-angle (atan (- (cadr second) (cadr first)) (- (car second) (car first))))
        (if (< label-angle 0.0) (setq label-angle (+ label-angle (* 2.0 pi))))
        (if (and (> label-angle (/ pi 2.0)) (<= label-angle (* 1.5 pi))) (setq label-angle (- label-angle pi)))
        (setq label-anchor (list (* 10.0 (/ (car label-midpoint)
                   (sqrt (+ (expt (car label-midpoint) 2) (expt (- (cadr label-midpoint) 1200.0) 2)))))
                (+ 1200.0 (* 10.0 (/ (- (cadr label-midpoint) 1200.0)
                   (sqrt (+ (expt (car label-midpoint) 2) (expt (- (cadr label-midpoint) 1200.0) 2)))))))
              labels (cons (list "3.21" label-anchor label-angle) labels))
        (foreach centre (list (ast:display-test-centre (car tail)) (ast:display-test-centre (cadr tail)))
          (if (not (member centre marked)) (setq marked (cons centre marked))))))
    (setq tail (cdr tail)))
  (ast:cad-test-assert (and valid (= 3 changed) (= 4 (length marked))
                          (ast:display-test-crossbars output marked 1.0))
                      "Arc crossbars mark exactly the slits bordering independently measured corrected chords")
  (ast:cad-test-assert (and (= 3 (length labels)) (ast:display-test-spacing-labels output labels 1.0))
    "Adjusted arc labels report rounded chords on the guide with readable rotations")
  (entmake '((0 . "CIRCLE") (8 . "0") (10 50.0 1200.0 0.0) (40 . 10.0)))
  (setq guide (entlast) result (ast:cad-generate guide settings nil) output (ast:cad-get 'output result))
  (ast:cad-test-assert (and (ast:cad-get 'ok result) (ast:display-test-chain output T))
                      "Closed-circle thread returns to its original slit exactly once")
  (setq corner-x (* 0.75 (sin (* pi (/ 40.0 180.0))))
        before-x (+ -3.0 (* 0.75 (cos (* pi (/ 40.0 180.0)))) corner-x)
        after-y (+ 1300.0 -3.0 (* 0.75 (cos (* pi (/ 40.0 180.0)))) (- corner-x)))
  (entmake (list '(0 . "LWPOLYLINE") '(100 . "AcDbEntity") '(8 . "0") '(100 . "AcDbPolyline")
                  '(90 . 3) '(70 . 0) (list 10 before-x 1300.0) '(10 0.0 1300.0) (list 10 0.0 after-y)))
  (setq guide (entlast) result (ast:cad-generate guide settings nil) output (ast:cad-get 'output result))
  (ast:cad-test-assert (and (ast:cad-get 'ok result) (= 3 (ast:cad-test-block-cuts output))
                          (= 1 (length (ast:display-test-entities output "AUTOSTITCH" "CIRCLE")))
                          (ast:display-test-chain output nil))
                      "Sharp corner has two thread segments meeting its actual round hole")
  (setq expected-virtuals (list
    (list '(type . slit) (cons 'center (list (+ before-x 3.0) 1300.0))
      (cons 'axis (list (cos (* pi (/ 40.0 180.0))) (sin (* pi (/ 40.0 180.0))))) '(length . 1.5))
    (list '(type . slit) (cons 'center (list 0.0 (+ after-y 3.0)))
      (cons 'axis (list (sin (* pi (/ 40.0 180.0))) (- (cos (* pi (/ 40.0 180.0)))))) '(length . 1.5)))
        state (ast:cad-read guide) solution (ast:g-solve (ast:cad-get 'route state) settings nil)
        virtuals (ast:cad-get 'virtual-slits solution)
        hole (ast:display-test-xy (cdr (assoc 10 (car (ast:display-test-entities output "AUTOSTITCH" "CIRCLE"))))))
  (ast:cad-test-assert (and (= 2 (length virtuals))
    (equal (mapcar '(lambda (item) (cdr (assoc 'center item))) virtuals)
           (mapcar '(lambda (item) (cdr (assoc 'center item))) expected-virtuals) 1e-8)
    (equal hole (mapcar '- (cdr (assoc 'center (car virtuals)))
                  (mapcar '(lambda (value) (* 0.75 value)) (cdr (assoc 'axis (car virtuals))))) 1e-8)
    (equal hole (mapcar '+ (cdr (assoc 'center (cadr virtuals)))
                  (mapcar '(lambda (value) (* 0.75 value)) (cdr (assoc 'axis (cadr virtuals))))) 1e-8)
    (ast:display-test-construction output expected-virtuals 1.0))
    "Sharp-corner construction shows both true virtual slits dashed with selected tips at the round-hole centre")
  (ast:cad-test-assert (and (ast:display-test-round-fills output 1.0)
    (null (vl-remove-if-not '(lambda (item) (equal 0 (cdr (assoc 70 item))))
      (ast:display-test-entities output "AUTOSTITCH" "LWPOLYLINE"))))
    "Round hole has an exact filled black disk; derived corner distances receive no spacing crossbars")
  (ast:cad-test-assert (and
    (vl-every '(lambda (item) (member (cdr (assoc 8 item)) '("AUTOSTITCH" "AUTOSTITCH_STITCHES")))
      (ast:display-test-entities output nil nil))
    (vl-every 'ast:display-test-visible '("AUTOSTITCH" "AUTOSTITCH_STITCHES"))
    (= 0 (cdr (assoc 290 (entget (tblobjname "LAYER" "AUTOSTITCH_UI")))))
    (ast:display-test-dashes output) (ast:display-test-round-fills output 1.0))
    "Printed openings and construction share AUTOSTITCH, thread stays separate, and editing markers remain nonprinting")
  (setq fills (ast:display-test-entities output "AUTOSTITCH" "LWPOLYLINE")
        dashes (ast:display-test-dashes output))
  (if (and fills dashes)
    (progn
      (setq original-data (car fills))
      (entmod (ast:cad-put 43 0.3 original-data))
      (ast:cad-test-assert (ast:cad-get 'stale (ast:cad-read guide)) "Edited round-hole fill is detected by output signature")
      (entmod original-data)
      (setq original-data (car dashes))
      (entmod (ast:cad-put 10 (mapcar '+ (cdr (assoc 10 original-data)) '(0.1 0.0 0.0)) original-data))
      (ast:cad-test-assert (ast:cad-get 'stale (ast:cad-read guide)) "Edited virtual-slit dash is detected by output signature")
      (entmod original-data)))
  (entmake (list '(0 . "LINE") '(8 . "0") (list 10 before-x 1330.0 0.0) '(11 0.0 1330.0 0.0)))
  (setq first (entlast))
  (entmake (list '(0 . "LINE") '(8 . "0") '(10 0.0 1330.0 0.0) (list 11 0.0 (+ after-y 30.0) 0.0)))
  (setq second (entlast) result (ast:cad-connect first second '(0.0 1330.0 0.0) settings nil)
        output (ast:cad-get 'output result)
        expected-virtuals (mapcar '(lambda (item) (ast:cad-put 'center
          (mapcar '+ (cdr (assoc 'center item)) '(0.0 30.0)) item)) expected-virtuals))
  (ast:cad-test-assert (and (ast:cad-get 'ok result) (= 3 (ast:cad-test-block-cuts output))
    (ast:display-test-construction output expected-virtuals 1.0) (ast:display-test-round-fills output 1.0))
    "Separate connected lines retain the same two virtual slits and one filled corner hole")
  (entmake '((0 . "LINE") (8 . "0") (10 -10.5 1400.0 0.0) (11 10.5 1400.0 0.0)))
  (setq first (entlast))
  (entmake '((0 . "LINE") (8 . "0") (10 0.0 1400.0 0.0) (11 0.0 1410.5 0.0)))
  (setq second (entlast) result (ast:cad-connect first second '(0.0 1400.0 0.0) settings nil)
        output (ast:cad-get 'output result))
  (ast:cad-test-assert (and (ast:cad-get 'ok result) (= 13 (ast:cad-test-block-cuts output))
                          (null (ast:display-test-entities output "AUTOSTITCH_UI" "TEXT"))
                          (ast:display-test-t-threads (ast:display-test-entities output "AUTOSTITCH_STITCHES" "LINE")))
                      "Connected T draws only its twelve true intervals; no cross-arm thread")
  (ast:cad-test-assert (and (null (ast:display-test-dashes output))
    (ast:display-test-round-fills output 1.0))
    "A branch has a filled shared hole without inventing virtual-slit construction")
  (setq result (ast:cad-generate second (ast:cad-put 'reverse T settings) nil))
  (ast:cad-test-assert (and (ast:cad-get 'ok result)
                          (ast:display-test-t-threads (ast:display-test-entities output "AUTOSTITCH_STITCHES" "LINE")))
                      "Reversing a connected member preserves physical thread-tip selection")
  (entmake (list '(0 . "ARC") '(8 . "0") '(10 20.0 1500.0 0.0) '(40 . 2.0) '(50 . 0.0) (cons 51 (/ pi 2.0))))
  (setq guide (entlast) result (ast:cad-generate guide settings nil) output (ast:cad-get 'output result))
  (ast:cad-test-assert (and (ast:cad-get 'ok result) (= 2 (ast:cad-test-block-cuts output))
                          (ast:display-test-crossbars output
                            (mapcar 'ast:display-test-centre (ast:display-test-openings output "LINE")) 1.0))
                      "Tight counterclockwise arc places four crossbars directly on its physical slit tips")
  (setq result (ast:cad-generate guide (ast:cad-put 'reverse T settings) nil))
  (ast:cad-test-assert (and (ast:cad-get 'ok result)
                          (ast:display-test-crossbars output
                            (mapcar 'ast:display-test-centre (ast:display-test-openings output "LINE")) 1.0))
                      "Reversing a tight arc retains crossbars on both ends of the same physical slits")
  (entmake (list '(0 . "ARC") '(8 . "0") '(10 30.0 1500.0 0.0) '(40 . 1.5) '(50 . 0.0) (cons 51 (* pi (/ 150.0 180.0)))))
  (setq guide (entlast) result (ast:cad-generate guide settings nil) output (ast:cad-get 'output result))
  (ast:cad-test-assert (and (ast:cad-get 'ok result) (= 2 (ast:cad-test-block-cuts output))
                          (ast:display-test-crossbars output
                            (mapcar 'ast:display-test-centre (ast:display-test-openings output "LINE")) 1.0))
                      "Tight 150-degree arc marks only its two actual slits")
  (setq result (ast:cad-generate guide (ast:cad-put 'reverse T settings) nil))
  (ast:cad-test-assert (and (ast:cad-get 'ok result)
                          (ast:display-test-crossbars output
                            (mapcar 'ast:display-test-centre (ast:display-test-openings output "LINE")) 1.0))
                      "Reversed 150-degree arc keeps local crossbars correctly oriented")
  (entmake '((0 . "LWPOLYLINE") (100 . "AcDbEntity") (8 . "0") (100 . "AcDbPolyline")
    (90 . 3) (70 . 0) (10 -8.660254037844386 1595.0) (42 . -0.2679491924311227)
    (10 0.0 1600.0) (42 . -0.2679491924311227) (10 -4.0 1593.0717967697245)))
  (setq guide (entlast) state (ast:cad-read guide) primitives (ast:cad-get 'primitives (ast:cad-get 'route state))
        corner (ast:g-corner (car primitives) (cadr primitives) settings)
        virtuals (ast:cad-get 'virtual-slits corner)
        curved-settings (ast:cad-put 'start (ast:cad-get 'incoming-station corner)
          (ast:cad-put 'end (+ (ast:g-length (car primitives)) (ast:cad-get 'outgoing-station corner)) settings))
        result (ast:cad-generate guide curved-settings nil) output (ast:cad-get 'output result))
  (ast:cad-test-assert (and (ast:cad-get 'ok result) (= 3 (ast:cad-test-block-cuts output))
    (= 2 (length virtuals))
    (equal (distance '(0.0 1590.0) (cdr (assoc 'center (car virtuals)))) 10.0 1e-8)
    (equal (distance '(-8.0 1600.0) (cdr (assoc 'center (cadr virtuals)))) 8.0 1e-8)
    (ast:display-test-construction output virtuals 1.0) (ast:display-test-round-fills output 1.0))
    "Arc-to-arc junction keeps virtual centres on their support circles and emits their dashed slit axes")
  (setvar "INSUNITS" 1)
  (entmake (list '(0 . "LINE") '(8 . "0") '(10 0.0 60.0 0.0) (list 11 (/ 30.5 25.4) 60.0 0.0)))
  (setq guide (entlast) result (ast:cad-generate guide settings nil) output (ast:cad-get 'output result)
        holes (ast:display-test-openings output "LINE")
        stations '(0.0 3.0 6.0 9.0 12.0 15.25 18.5 21.5 24.5 27.5 30.5) valid T)
  (foreach data holes
    (if (or (null stations)
            (not (equal (ast:display-test-centre data) (list (/ (car stations) 25.4) 60.0) 1e-8))
            (not (equal (distance (cdr (assoc 10 data)) (cdr (assoc 11 data))) (/ 1.5 25.4) 1e-8)))
      (setq valid nil))
    (setq stations (cdr stations)))
  (ast:cad-test-assert (and (ast:cad-get 'ok result) (= 11 (length holes)) valid (null stations)
                          (ast:display-test-chain output nil))
                      "Inch drawing scales every slit centre, slit length and thread endpoint")
  (setq marked (mapcar '(lambda (station) (list (/ station 25.4) 60.0)) '(12.0 15.25 18.5)))
  (ast:cad-test-assert (ast:display-test-crossbars output marked 25.4)
                      "Inch drawing scales crossbar positions and footprint while retaining the slit lineweight")
  (setq labels (list (list "3.25" (list (/ 13.625 25.4) 60.0) 0.0)
                     (list "3.25" (list (/ 16.875 25.4) 60.0) 0.0)))
  (ast:cad-test-assert (ast:display-test-spacing-labels output labels 25.4)
    "Inch drawing scales spacing-label placement and height while values remain millimetres")
  (setq result (ast:cad-generate guide (ast:cad-put 'reverse T settings) nil))
  (ast:cad-test-assert (and (ast:cad-get 'ok result) (ast:display-test-crossbars output marked 25.4))
                      "Reversed straight line retains the same six monochrome crossbars")
  (ast:cad-test-assert (ast:display-test-spacing-labels output labels 25.4)
    "Reversing the guide keeps spacing values upright at the same physical positions")
  (entmake (list '(0 . "LWPOLYLINE") '(100 . "AcDbEntity") '(8 . "0") '(100 . "AcDbPolyline")
    '(90 . 3) '(70 . 0) (list 10 (/ before-x 25.4) 70.0) '(10 0.0 70.0)
    (list 10 0.0 (+ 70.0 (/ (- after-y 1300.0) 25.4)))))
  (setq guide (entlast) result (ast:cad-generate guide settings nil) output (ast:cad-get 'output result)
        state (ast:cad-read guide) solution (ast:g-solve (ast:cad-get 'route state) settings nil))
  (ast:cad-test-assert (and (ast:cad-get 'ok result) (= 3 (ast:cad-test-block-cuts output))
    (ast:display-test-construction output (ast:cad-get 'virtual-slits solution) 25.4)
    (ast:display-test-round-fills output 25.4))
    "Inch drawing scales virtual-slit dashes and filled-hole diameter without scaling lineweights")
  ;; The reported shallow corner: connecting saves inputs; Generate fits and marks the exception.
  (setvar "INSUNITS" 4)
  (setq first (entmakex '((0 . "LINE") (8 . "0") (10 -38.0 258.0 0.0)
    (11 107.80342046542515 215.04231639645309 0.0)))
    second (entmakex '((0 . "LINE") (8 . "0") (10 107.80342046542515 215.04231639645309 0.0)
    (11 285.06457440910435 231.24365283994626 0.0)))
    result (ast:cad-connect-guides first second nil settings nil))
  (ast:cad-test-assert (and (ast:cad-get 'ok result)
    (null (ast:cad-get 'output (ast:cad-read first)))
    (null (ast:cad-get 'output (ast:cad-read second))))
    "The reported shallow-corner guides connect without creating any stitching")
  (setq result (ast:cad-generate first settings nil) output (ast:cad-get 'output result)
    primitives (ast:cad-get 'primitives (ast:cad-get 'route (ast:cad-read second)))
    expected (ast:g-ends (ast:g-slit (car primitives) 0.0 settings)) marked nil)
  (foreach data (ast:display-test-crossbar-entities output)
    (setq notes (ast:display-test-polyline-vertices data)
      centre (mapcar '(lambda (aa bb) (/ (+ aa bb) 2.0)) (car notes) (cadr notes)))
    (if (vl-some '(lambda (tip) (equal tip centre 1e-8)) expected)
      (setq marked (cons centre marked))))
  (ast:cad-test-assert (and (ast:cad-get 'ok result) (= 2 (length marked))
    (vl-every '(lambda (tip) (vl-some '(lambda (point) (equal tip point 1e-8)) marked)) expected)
    (not (ast:cad-get 'stale (ast:cad-read first))))
    "The adjusted corner neighbour has an I mark at both slit tips and complete current output")
  (setq label-angle (atan (- 231.24365283994626 215.04231639645309) (- 285.06457440910435 107.80342046542515))
        label-anchor (list (- 107.80342046542515 (* 0.5 3.097120227 (cos label-angle)))
                           (- 215.04231639645309 (* 0.5 3.097120227 (sin label-angle))))
        labels (ast:display-test-entities output "AUTOSTITCH_UI" "TEXT"))
  (ast:cad-test-assert (vl-some '(lambda (data)
    (and (= "3.10" (cdr (assoc 1 data)))
      (equal label-anchor (ast:display-test-xy (cdr (assoc 11 data))) 1e-7))) labels)
    "Adjusted corner label measures the virtual-to-real step rather than the round-hole gap")
  (setq original-dimzin (getvar "DIMZIN"))
  (foreach changed '(0 8 12)
    (setvar "DIMZIN" changed)
    (ast:cad-test-assert (equal '("10.00" "3.25" "0.13")
      (mapcar 'ast:cad-spacing-label '(10.0 3.25 0.125)))
      "Spacing values use two decimal places without depending on drawing dimension suppression"))
  (setvar "DIMZIN" original-dimzin)
  (setvar "FILLMODE" original-fill)
  (setvar "LWDISPLAY" original-lineweight)
  (setvar "INSUNITS" original-units)
  (list (cons 'passed ast:*cad-test-passed*) (cons 'failed (length ast:*cad-test-failures*))
        (cons 'failures (reverse ast:*cad-test-failures*))))
(princ)
