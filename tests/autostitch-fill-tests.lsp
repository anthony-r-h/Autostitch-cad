;;; Shared recipe qualification; pure core solves, no drawing writes.
(defun ast:fill-test-route (vertices / primitives point next bulge chord middle offset center radius closed)
  (setq closed (equal (list (caar vertices) (cadar vertices)) (list (car (last vertices)) (cadr (last vertices))) 1e-9))
  (while (cdr vertices)
    (setq point (list (caar vertices) (cadar vertices)) next (list (caadr vertices) (cadadr vertices))
      bulge (if (caddar vertices) (caddar vertices) 0.0))
    (if (equal bulge 0.0 1e-12)
      (setq primitives (append primitives (list (list '(kind . line) (cons 'a point) (cons 'b next)))))
      (progn
        (setq chord (distance point next) middle (ast:g-mul (ast:g-add point next) 0.5)
          offset (/ (* chord (- 1.0 (* bulge bulge))) (* 4.0 bulge))
          center (ast:g-add middle (ast:g-mul (ast:g-left (ast:g-sub next point)) (/ offset chord)))
          radius (distance center point))
        (setq primitives (append primitives (list (list '(kind . arc) (cons 'center center) (cons 'radius radius)
          (cons 'start-angle (atan (- (cadr point) (cadr center)) (- (car point) (car center))))
          (cons 'sweep (* 4.0 (atan bulge)))))))))
    (setq vertices (cdr vertices)))
  (list (cons 'primitives primitives) (cons 'closed closed)))
(defun ast:fill-test-solve (kind parameters / settings paths vertices index tail other nodes connections node incidence incidences result openings intervals error route radius path-settings landmarks solutions)
  (setq settings (ast:cad-default-settings) index 0)
  (foreach vertices (ast:fill-paths kind parameters)
    (setq route (ast:fill-test-route vertices) path-settings settings landmarks nil)
    (if (= kind "CIRCLES")
      (progn
        (setq radius (ast:g-get 'radius (car (ast:g-get 'primitives route nil)) nil)
          landmarks (list '((primitive . 0) (station . 0.0)) (list '(primitive . 0) (cons 'station (* pi radius)))))
        (if (>= (* 2.0 radius) (ast:g-get 'pitch settings 3.0))
          (setq path-settings (ast:fill-circle-settings radius settings)))))
    (setq paths (append paths (list (list (cons 'id index) (cons 'route route)
      (cons 'settings path-settings) (cons 'landmarks landmarks)))) index (1+ index)))
  (if (member kind '("QUILT" "MAZE"))
    (progn
      (setq tail paths)
      (while tail
        (foreach other (cdr tail)
          (setq result (ast:g-connect-candidates (ast:g-get 'route (car tail) nil) (ast:g-get 'route other nil)))
          (ast:cad-require (ast:g-get 'ok result nil) (ast:g-get 'error result nil))
          (setq nodes (ast:g-get 'connections result nil))
          (foreach node nodes
            (setq incidences nil)
            (foreach incidence (ast:g-get 'incidences node nil)
              (setq incidences (append incidences (list (ast:n-put 'path
                (ast:g-get 'id (if (= 0 (ast:g-get 'path incidence nil)) (car tail) other) nil) incidence)))))
            (setq connections (ast:cad-merge-connection connections
              (list (cons 'point (ast:g-get 'point node nil)) (cons 'incidences incidences))))))
        (setq tail (cdr tail)))
      (ast:g-solve-set paths (ast:cad-number-connections connections)))
    (progn
      (foreach other paths
        (if (null error)
          (progn
            (setq result (ast:g-solve (ast:g-get 'route other nil) (ast:g-get 'settings other nil) (ast:g-get 'landmarks other nil)))
            (if (ast:g-get 'ok result nil)
              (setq openings (append openings (ast:g-get 'openings result nil)) intervals (append intervals (ast:g-get 'intervals result nil)) solutions (cons result solutions))
              (setq error (ast:g-get 'error result nil))))))
      (if (null error) (setq error (ast:g-validate-openings openings settings)))
      (if error (ast:g-error error) (list '(ok . T) (cons 'openings openings) (cons 'intervals intervals) (cons 'solutions solutions))))))
(defun ast:fill-test-circle-balance (solution / half gaps)
  (setq half (* pi (ast:g-get 'radius (car (ast:g-get 'primitives solution nil)) 0.0))
    gaps (vl-remove-if-not '(lambda (gap) (= 'corrected (ast:g-get 'kind gap nil))) (ast:g-get 'intervals solution nil)))
  (and gaps (vl-every '(lambda (gap)
    (vl-some '(lambda (other)
      (and (< (abs (- (ast:g-get 'distance gap 0.0) (ast:g-get 'distance other 0.0))) 1e-8)
        (< (abs (- (abs (- (ast:g-get 'start-station gap 0.0) (ast:g-get 'start-station other 0.0))) half)) 1e-7))) gaps)) gaps)))
(defun ast:fill-test-check (condition label)
  (setq ast:fill-test-count (1+ ast:fill-test-count))
  (if (not condition) (setq ast:fill-test-failures (cons label ast:fill-test-failures))))
(defun ast:fill-tests (/ ast:fill-test-count ast:fill-test-failures result fixture gaps-ok interval distance paths points)
  (setq ast:fill-test-count 0 ast:fill-test-failures nil gaps-ok T)
  (foreach fixture '(("CIRCLES" "Concentric circles solve at 3 mm")
      ("QUILT" "Quilt fill solves at 3 mm") ("MAZE" "Maze fill solves at 3 mm") ("FLOW" "Flow fill solves at 3 mm"))
    (setq result (ast:fill-test-solve (car fixture) nil))
    (ast:fill-test-check (ast:g-get 'ok result nil) (cadr fixture))
    (foreach interval (ast:g-get 'intervals result nil)
      (if (/= 'junction (ast:g-get 'kind interval nil))
        (progn (setq distance (ast:g-get 'distance interval 0.0))
          (if (or (< distance (- 2.7 1e-8)) (> distance (+ 3.3 1e-8))) (setq gaps-ok nil)))))
    (if (= (car fixture) "MAZE")
      (progn
        (ast:fill-test-check (and (= 82 (length (ast:g-get 'openings result nil)))
          (= 7 (length (vl-remove-if-not '(lambda (opening) (= 'round (ast:g-get 'type opening nil)))
            (ast:g-get 'openings result nil)))))
          "Maze has 82 openings with 7 shared junction holes")
        (ast:fill-test-check (and
          (vl-every '(lambda (gap) (< (abs (- (ast:g-get 'distance gap 0.0)
            (if (= 'junction (ast:g-get 'kind gap nil)) 1.5 3.0))) 1e-8)) (ast:g-get 'intervals result nil))
          (not (vl-some '(lambda (gap) (= 'corrected (ast:g-get 'kind gap nil))) (ast:g-get 'intervals result nil))))
          "Maze reserves half pitch at junctions and nominal gaps elsewhere")
        (setq paths (ast:fill-paths "MAZE" nil) points (apply 'append paths))
        (ast:fill-test-check (and
          (= 0.0 (apply 'min (mapcar 'car points)) (apply 'min (mapcar 'cadr points)))
          (= 36.0 (apply 'max (mapcar 'car points))) (= 30.0 (apply 'max (mapcar 'cadr points)))
          (vl-every '(lambda (point) (and (= (car point) (* 1.5 (fix (/ (car point) 1.5))))
            (= (cadr point) (* 1.5 (fix (/ (cadr point) 1.5)))))) points)
          (vl-every '(lambda (opening / point)
            (setq point (ast:g-get 'center opening nil))
            (or (/= 'round (ast:g-get 'type opening nil))
              (and (= (car point) (* 6.0 (fix (/ (car point) 6.0))))
                (= (cadr point) (* 6.0 (fix (/ (cadr point) 6.0))))))) (ast:g-get 'openings result nil))
          (vl-every '(lambda (path) (and (= 2 (length path))
            (or (= (caar path) (caadr path)) (= (cadar path) (cadadr path))))) paths))
          "Maze junctions stay on a 6 mm grid with half-pitch free-end insets")
        (ast:fill-test-check (= 5 (length (ast:cad-components (length paths) (ast:g-get 'connections result nil))))
          "Maze wall network has five connected groups")))
    (if (= (car fixture) "FLOW")
      (progn
        (ast:fill-test-check (and (= 300 (length (ast:g-get 'intervals result nil)))
          (vl-every '(lambda (gap) (< (abs (- (ast:g-get 'distance gap 0.0) 3.0)) 1e-8))
            (ast:g-get 'intervals result nil))
          (not (vl-some '(lambda (gap) (= 'corrected (ast:g-get 'kind gap nil))) (ast:g-get 'intervals result nil))))
          "Flow uses 300 nominal gaps without adjusted spacing")
        (setq paths (ast:fill-paths "FLOW" nil))
        (ast:fill-test-check (vl-every '(lambda (path)
          (and (> (caar path) 6.0) (< (caadr path) 42.0))) paths)
          "Flow free ends stop inside the original curve bounds")))
    (if (= (car fixture) "CIRCLES")
      (progn
        (ast:fill-test-check (not (vl-some '(lambda (opening) (= 'round (ast:g-get 'type opening nil))) (ast:g-get 'openings result nil)))
          "Concentric circles have no round corner holes")
        (ast:fill-test-check (and
          (= 10 (length (vl-remove-if-not '(lambda (gap) (ast:g-get 'reserved gap nil)) (ast:g-get 'intervals result nil))))
          (vl-every '(lambda (gap) (or (not (ast:g-get 'reserved gap nil))
            (< (abs (- (ast:g-get 'distance gap 0.0) 3.0)) 1e-8))) (ast:g-get 'intervals result nil)))
          "Circle diameter landmarks reserve ten nominal gaps")
        (ast:fill-test-check (and (= 5 (length (ast:g-get 'solutions result nil)))
          (vl-every 'ast:fill-test-circle-balance (ast:g-get 'solutions result nil)))
          "Circle adjustments match on opposite halves")))
    (if (= (car fixture) "QUILT")
      (ast:fill-test-check (= 64 (length (vl-remove-if-not '(lambda (opening) (= 'round (ast:g-get 'type opening nil))) (ast:g-get 'openings result nil))))
        "Quilt shares one round hole at each of 64 crossings")))
  (ast:fill-test-check gaps-ok "All unprotected fill gaps stay within pitch allowance")
  (setq result (ast:g-solve (ast:fill-test-route '((0.0 0.0) (7.0 0.0))) (ast:cad-default-settings) nil))
  (ast:fill-test-check (not (ast:g-get 'ok result nil)) "Seven millimetre clipped run is rejected at 3 mm pitch")
  (setq result (ast:fill-test-solve "CIRCLES" '((inner-radius . 1.0))))
  (ast:fill-test-check (not (ast:g-get 'ok result nil)) "Circle radius below half the pitch is rejected")
  (setq result (ast:fill-test-solve "QUILT" '((crossing-spacing . 7.0))))
  (ast:fill-test-check (not (ast:g-get 'ok result nil)) "Seven millimetre quilt junction spacing is rejected")
  (list (cons 'ok (null ast:fill-test-failures)) (cons 'passed (- ast:fill-test-count (length ast:fill-test-failures)))
    (cons 'failed (length ast:fill-test-failures)) (cons 'failures (reverse ast:fill-test-failures))))
(princ)
