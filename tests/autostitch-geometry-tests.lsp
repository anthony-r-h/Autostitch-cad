;;; Load core first. (ast:g-tests) returns a result alist and does not touch CAD.
(defun ast:g-test (condition label)
  (setq ast:g-test-count (1+ ast:g-test-count))
  (if (not condition) (setq ast:g-test-failures (cons label ast:g-test-failures))))
(defun ast:g-test-stitch-hand (/ primitive face hand settings axis expected route result reference)
  (setq primitive '((kind . line) (a 0.0 0.0) (b 30.0 0.0)))
  (foreach face '(1 -1)
    (foreach hand '(1 -1)
      (setq settings (list (cons 'handedness face) (cons 'stitch-hand hand))
            axis (ast:g-axis primitive 0.0 settings)
            expected (list (cos (* pi (/ 40.0 180.0))) (* face hand (sin (* pi (/ 40.0 180.0))))))
      (ast:g-test (equal axis expected 1e-10) "Stitch lean and material face independently determine the slit axis")
      (ast:g-test (ast:g-same-opening (ast:g-slit primitive 12.0 settings)
        (ast:g-slit (ast:g-reverse-primitive primitive) 18.0 settings))
        "Travel reversal preserves the physical slit axis for both stitch leans and faces")
      (foreach route '(((primitives ((kind . line) (a 0.0 0.0) (b 30.0 0.0))))
                       ((primitives ((kind . arc) (center 0.0 0.0) (radius . 20.0) (start-angle . 0.0) (sweep . 6.283185307179586))) (closed . T))
                       ((primitives ((kind . line) (a 0.0 0.0) (b 30.0 0.0)) ((kind . line) (a 30.0 0.0) (b 30.0 30.0))))
                       ((primitives ((kind . line) (a -30.0 0.0) (b 0.0 0.0)) ((kind . arc) (center -20.0 0.0) (radius . 20.0) (start-angle . 0.0) (sweep . 1.5)))))
        (setq result (ast:g-solve route settings nil)
              reference (ast:g-solve route (list (cons 'handedness (* face hand))) nil))
        (ast:g-test (and (ast:g-get 'ok result nil) (equal result reference 1e-8))
          "Both stitch leans preserve fitting and corner construction on lines curves and closed loops"))))
  (ast:g-test (ast:g-profile-error '((stitch-hand . 0))) "Invalid stitch lean is rejected before solving")
  (ast:g-test (equal (ast:g-solve (list (cons 'primitives (list primitive))) nil nil)
    (ast:g-solve (list (cons 'primitives (list primitive))) '((stitch-hand . 1)) nil))
    "Legacy settings without stitch lean retain obverse geometry"))

(defun ast:g-test-guide (radius sigma tangent-angle extent incoming / tangent center radial angle)
  (setq tangent (list (cos tangent-angle) (sin tangent-angle)))
  (if (= radius 0)
    (if incoming (list '(kind . line) (cons 'a (ast:g-mul tangent (- extent))) '(b 0.0 0.0))
      (list '(kind . line) '(a 0.0 0.0) (cons 'b (ast:g-mul tangent extent))))
    (progn
      (setq center (ast:g-mul (ast:g-left tangent) (* sigma radius)) radial (ast:g-mul (ast:g-left tangent) (- sigma))
            angle (atan (cadr radial) (car radial)))
      (list '(kind . arc) (cons 'center center) (cons 'radius radius)
            (cons 'start-angle (if incoming (- angle (* sigma (/ extent radius))) angle)) (cons 'sweep (* sigma (/ extent radius)))))))
;; Independent endpoint/tangent evaluation for corner checks: no production locus,
;; station recovery, point, tangent, or slit builder is used here.
(defun ast:g-test-corner-slit (radius sigma tangent station / angle center)
  (setq angle (+ tangent (if (= radius 0.0) 0.0 (* sigma (/ station radius)))))
  (setq center
    (if (= radius 0.0) (list (* station (cos tangent)) (* station (sin tangent)))
      (list (+ (* (- sigma) radius (sin tangent)) (* sigma radius (sin angle)))
            (- (* sigma radius (cos tangent)) (* sigma radius (cos angle))))))
  (list center (list (cos (+ angle (* pi (/ 40.0 180.0)))) (sin (+ angle (* pi (/ 40.0 180.0)))))))
(defun ast:g-test-chord-station (radius pitch)
  (if (= radius 0.0) pitch (* 2.0 radius (atan pitch (sqrt (- (* 4.0 radius radius) (* pitch pitch)))))))
(defun ast:g-test-corner-matrix (/ pitch hand degrees angle settings incoming outgoing corner expected point label radius-in radius-out sigma-in sigma-out extent-in extent-out station-in station-out before after virtual-in virtual-out joint route result reversed-result)
  ;; Closed-form line intersection, independently of the production generic loci.
  (foreach pitch '(2.7 3.0 3.38 3.85)
    (foreach hand '(-1 1)
      (foreach degrees '(-150 -135 -120 -90 -60 -45 -30 30 45 60 90 120 135 150)
        (setq angle (* pi (/ degrees 180.0))
              settings (list (cons 'pitch pitch) (cons 'handedness hand))
              incoming (ast:g-test-guide 0.0 1 0.0 30.0 T)
              outgoing (ast:g-test-guide 0.0 1 angle 30.0 nil)
              corner (ast:g-corner incoming outgoing settings)
              label (strcat "line corner p=" (rtos pitch 2 2) " turn=" (itoa degrees) " hand=" (itoa hand))
              expected (list (/ (* -0.75 hand (sin (* pi (/ 40.0 180.0))) (cos (/ angle 2.0))) (sin (/ angle 2.0)))
                             (* -0.75 hand (sin (* pi (/ 40.0 180.0))))))
        (ast:g-test (ast:g-get 'ok corner nil) (strcat label " accepted"))
        (if (ast:g-get 'ok corner nil)
          (progn
            (setq point (ast:g-get 'center (ast:g-get 'opening corner nil) nil))
            (ast:g-test (equal point expected 1e-8) (strcat label " closed-form hole"))
            (ast:g-test (and (equal (ast:g-get 'incoming-station corner nil)
                                   (+ 30.0 (car expected) (* 0.75 (cos (* pi (/ 40.0 180.0)))) (- pitch)) 1e-8)
                             (equal (ast:g-get 'outgoing-station corner nil)
                                    (+ (* (car expected) (cos angle)) (* (cadr expected) (sin angle)) (- (* 0.75 (cos (* pi (/ 40.0 180.0))))) pitch) 1e-8))
                        (strcat label " nominal virtual-to-real neighbours")))))))
  ;; Mixed-curve cases independently reconstruct the selected virtual tips.
  (foreach degrees '(-135 -90 -45 45 90 135)
    (foreach radius-in '(0.0 10.0)
      (foreach radius-out '(0.0 8.0)
        (if (or (> radius-in 0.0) (> radius-out 0.0))
          (foreach sigma-in (if (= radius-in 0.0) '(1) '(-1 1))
            (foreach sigma-out (if (= radius-out 0.0) '(1) '(-1 1))
              (setq angle (* pi (/ degrees 180.0))
                    extent-in (if (= radius-in 0.0) 10.0 (* radius-in (/ pi 3.0)))
                    extent-out (if (= radius-out 0.0) 10.0 (* radius-out (/ pi 3.0)))
                    incoming (ast:g-test-guide radius-in sigma-in 0.0 extent-in T)
                    outgoing (ast:g-test-guide radius-out sigma-out angle extent-out nil)
                    corner (ast:g-corner incoming outgoing '((pitch . 3.0) (thickness . 0.2) (margin . 0.2)))
                    label (strcat "curved corner " (rtos radius-in 2 0) "/" (rtos radius-out 2 0) " turn=" (itoa degrees)
                                  " winding=" (itoa sigma-in) "/" (itoa sigma-out)))
              (ast:g-test (ast:g-get 'ok corner nil) (strcat label " accepted"))
              (if (ast:g-get 'ok corner nil)
                (progn
                  (setq station-in (- (ast:g-get 'incoming-station corner 0.0) extent-in)
                        station-out (ast:g-get 'outgoing-station corner 0.0)
                        before (ast:g-test-corner-slit radius-in sigma-in 0.0 station-in)
                        after (ast:g-test-corner-slit radius-out sigma-out angle station-out)
                        virtual-in (ast:g-test-corner-slit radius-in sigma-in 0.0 (+ station-in (ast:g-test-chord-station radius-in 3.0)))
                        virtual-out (ast:g-test-corner-slit radius-out sigma-out angle (- station-out (ast:g-test-chord-station radius-out 3.0)))
                        joint (ast:g-get 'center (ast:g-get 'opening corner nil) nil))
                  (ast:g-test (and (>= station-in (- (- extent-in) 1e-8)) (<= station-in 1e-8)
                                   (>= station-out -1e-8) (<= station-out (+ extent-out 1e-8))) (strcat label " finite arms"))
                  (ast:g-test (and (equal (distance (car before) (car virtual-in)) 3.0 1e-8)
                                   (equal (distance (car after) (car virtual-out)) 3.0 1e-8)) (strcat label " direct chord pitch"))
                  (ast:g-test (and (equal joint (mapcar '- (car virtual-in) (mapcar '(lambda (value) (* 0.75 value)) (cadr virtual-in))) 1e-8)
                                   (equal joint (mapcar '+ (car virtual-out) (mapcar '(lambda (value) (* 0.75 value)) (cadr virtual-out))) 1e-8))
                              (strcat label " independently reconstructed selected tips"))
                  (setq route (list (cons 'primitives
                                    (list (ast:g-test-guide radius-in sigma-in 0.0 (- station-in) T)
                                          (ast:g-test-guide radius-out sigma-out angle station-out nil))))
                        result (ast:g-solve route '((pitch . 3.0) (thickness . 0.2) (margin . 0.2)) nil))
                  (ast:g-test (and (ast:g-get 'ok result nil) (= 3 (length (ast:g-get 'openings result nil)))
                                   (= 2 (length (ast:g-get 'intervals result nil))))
                              (strcat label " full route ending at reserved neighbours: " (ast:g-get 'error result "")))
                  (setq reversed-result (ast:g-solve route '((pitch . 3.0) (thickness . 0.2) (margin . 0.2) (reverse . T)) nil))
                  (ast:g-test (and (ast:g-get 'ok result nil) (ast:g-get 'ok reversed-result nil)
                                   (= 3 (length (ast:g-get 'openings reversed-result nil)))
                                   (not (member nil (mapcar 'ast:g-same-opening (reverse (ast:g-get 'openings result nil))
                                                                          (ast:g-get 'openings reversed-result nil)))))
                              (strcat label " reversed route preserves physical openings: " (ast:g-get 'error reversed-result "")))))))))))
  (setq incoming (ast:g-test-guide 3.0 1 0.0 (* 3.0 (/ pi 2.0)) T)
        outgoing (ast:g-test-guide 3.0 1 (- (/ pi 4.0)) (* 3.0 (/ pi 2.0)) nil)
        corner (ast:g-corner incoming outgoing '((pitch . 3.0) (thickness . 0.2) (margin . 0.2))))
  (ast:g-test (ast:g-get 'ok corner nil) "R3 same winding 45 degree turn admits local corner")
  ;; Here the support centres are 6 cos(pi/8)=5.543277195 mm apart,
  ;; while the two selected-tip locus radii sum to only 5.165251497 mm.
  (setq incoming (ast:g-test-guide 3.0 -1 0.0 (* 3.0 (/ pi 2.0)) T)
        corner (ast:g-corner incoming outgoing '((pitch . 3.0) (thickness . 0.2) (margin . 0.2))))
  (ast:g-test (and (not (ast:g-get 'ok corner nil)) (wcmatch (ast:g-get 'error corner "") "*do not define one corner hole*"))
              "R3 opposite winding same 45 degree turn rejects disjoint loci")
  (setq outgoing (ast:g-test-guide 3.0 -1 (* pi -0.75) (* 3.0 (/ pi 2.0)) nil)
        corner (ast:g-corner incoming outgoing '((pitch . 3.0) (thickness . 0.2) (margin . 0.2))))
  (ast:g-test (and (not (ast:g-get 'ok corner nil)) (wcmatch (ast:g-get 'error corner "") "*Two stitch holes touch*"))
              "R3 same winding 135 degree turn rejects crossing real slit axes")
  (foreach degrees '(-180 -170 -160 160 170 180)
    (setq corner (ast:g-corner (ast:g-test-guide 0.0 1 0.0 30.0 T)
                               (ast:g-test-guide 0.0 1 (* pi (/ degrees 180.0)) 30.0 nil)
                               '((pitch . 3.0) (thickness . 0.2) (margin . 0.2))))
    (ast:g-test (not (ast:g-get 'ok corner nil)) (strcat "clearance or reversal rejects turn " (itoa degrees))))
  (foreach degrees '(-159.565 159.565)
    (setq corner (ast:g-corner (ast:g-test-guide 0.0 1 0.0 30.0 T)
                               (ast:g-test-guide 0.0 1 (* pi (/ degrees 180.0)) 30.0 nil)
                               '((pitch . 3.0) (thickness . 0.2) (margin . 0.2))))
    (ast:g-test (ast:g-get 'ok corner nil) (strcat "20.435 degree included angle clears 0.4 mm: " (rtos degrees 2 3))))
  (foreach degrees '(-159.566 159.566)
    (setq corner (ast:g-corner (ast:g-test-guide 0.0 1 0.0 30.0 T)
                               (ast:g-test-guide 0.0 1 (* pi (/ degrees 180.0)) 30.0 nil)
                               '((pitch . 3.0) (thickness . 0.2) (margin . 0.2))))
    (ast:g-test (not (ast:g-get 'ok corner nil)) (strcat "20.434 degree included angle fails 0.4 mm: " (rtos degrees 2 3))))
  (foreach degrees '(-22.4833 22.4833)
    (setq corner (ast:g-corner (ast:g-test-guide 0.0 1 0.0 30.0 T)
                               (ast:g-test-guide 0.0 1 (* pi (/ degrees 180.0)) 30.0 nil) '((pitch . 3.0) (corrections . nil))))
    (ast:g-test (not (ast:g-get 'ok corner nil)) (strcat "shallow turn neighbour leaves arm: " (rtos degrees 2 4))))
  (foreach degrees '(-22.4836 22.4836)
    (setq corner (ast:g-corner (ast:g-test-guide 0.0 1 0.0 30.0 T)
                               (ast:g-test-guide 0.0 1 (* pi (/ degrees 180.0)) 30.0 nil) '((pitch . 3.0))))
    (ast:g-test (ast:g-get 'ok corner nil) (strcat "shallow turn neighbour fits arm: " (rtos degrees 2 4)))))
(defun ast:g-test-rigid-point (point angle offset)
  (list (+ (car offset) (- (* (car point) (cos angle)) (* (cadr point) (sin angle))))
        (+ (cadr offset) (* (car point) (sin angle)) (* (cadr point) (cos angle)))))
(defun ast:g-test-rigid-primitive (primitive angle offset)
  (if (= (ast:g-get 'kind primitive nil) 'line)
    (list '(kind . line) (cons 'a (ast:g-test-rigid-point (ast:g-get 'a primitive nil) angle offset))
                       (cons 'b (ast:g-test-rigid-point (ast:g-get 'b primitive nil) angle offset)))
    (list '(kind . arc) (cons 'center (ast:g-test-rigid-point (ast:g-get 'center primitive nil) angle offset))
                       (cons 'radius (ast:g-get 'radius primitive nil))
                       (cons 'start-angle (+ (ast:g-get 'start-angle primitive nil) angle))
                       (cons 'sweep (ast:g-get 'sweep primitive nil)))))
(defun ast:g-test-rigid-opening (opening angle offset / transformed)
  (setq transformed (subst (cons 'center (ast:g-test-rigid-point (ast:g-get 'center opening nil) angle offset))
                           (assoc 'center opening) opening))
  (if (= (ast:g-get 'type opening nil) 'slit)
    (setq transformed (subst (cons 'axis (ast:g-test-rigid-point (ast:g-get 'axis opening nil) angle '(0.0 0.0)))
                             (assoc 'axis opening) transformed)))
  transformed)
;; Separate entry point for focused runs; also included by ast:g-tests below.
(defun ast:g-test-corner-transforms (/ ast:g-test-count ast:g-test-failures degrees radius-in radius-out sigma-in sigma-out angle extent-in extent-out incoming outgoing corner station-in station-out route baseline transform rotation offset transformed expected result label)
  (setq ast:g-test-count 0 ast:g-test-failures nil)
  (foreach degrees '(-135 -90 -45 45 90 135)
    (foreach radius-in '(0.0 10.0)
      (foreach radius-out '(0.0 8.0)
        (if (or (> radius-in 0.0) (> radius-out 0.0))
          (foreach sigma-in (if (= radius-in 0.0) '(1) '(-1 1))
            (foreach sigma-out (if (= radius-out 0.0) '(1) '(-1 1))
              (setq angle (* pi (/ degrees 180.0))
                    extent-in (if (= radius-in 0.0) 10.0 (* radius-in (/ pi 3.0)))
                    extent-out (if (= radius-out 0.0) 10.0 (* radius-out (/ pi 3.0)))
                    incoming (ast:g-test-guide radius-in sigma-in 0.0 extent-in T)
                    outgoing (ast:g-test-guide radius-out sigma-out angle extent-out nil)
                    corner (ast:g-corner incoming outgoing '((pitch . 3.0) (thickness . 0.2) (margin . 0.2)))
                    station-in (- (ast:g-get 'incoming-station corner 0.0) extent-in)
                    station-out (ast:g-get 'outgoing-station corner 0.0)
                    route (list (ast:g-test-guide radius-in sigma-in 0.0 (- station-in) T)
                                (ast:g-test-guide radius-out sigma-out angle station-out nil))
                    baseline (ast:g-solve (list (cons 'primitives route)) '((pitch . 3.0) (thickness . 0.2) (margin . 0.2)) nil)
                    label (strcat "rigid corner " (rtos radius-in 2 0) "/" (rtos radius-out 2 0) " turn=" (itoa degrees)
                                  " winding=" (itoa sigma-in) "/" (itoa sigma-out)))
              (ast:g-test (and (ast:g-get 'ok baseline nil) (= 3 (length (ast:g-get 'openings baseline nil)))) (strcat label " baseline"))
              (foreach transform '((0.37 (0.0 0.0)) (0.37 (123.4 -56.7)) (0.37 (1000.0 1000.0)))
                (setq rotation (car transform) offset (cadr transform)
                      transformed (mapcar '(lambda (item) (ast:g-test-rigid-primitive item rotation offset)) route)
                      expected (mapcar '(lambda (item) (ast:g-test-rigid-opening item rotation offset)) (ast:g-get 'openings baseline nil))
                      result (ast:g-solve (list (cons 'primitives transformed)) '((pitch . 3.0) (thickness . 0.2) (margin . 0.2)) nil))
                (ast:g-test (and (ast:g-get 'ok result nil) (= 3 (length (ast:g-get 'openings result nil)))
                                 (= 2 (length (ast:g-get 'intervals result nil))))
                            (strcat label " moved " (vl-princ-to-string offset) ": " (ast:g-get 'error result "")))
                (ast:g-test (and (= 3 (length expected)) (= 3 (length (ast:g-get 'openings result nil)))
                                 (not (member nil (mapcar 'ast:g-same-opening expected (ast:g-get 'openings result nil)))))
                            (strcat label " transformed centres/types/axes " (vl-princ-to-string offset))))))))))
  (list (cons 'ok (null ast:g-test-failures)) (cons 'checks ast:g-test-count) (cons 'failures (reverse ast:g-test-failures))))
(defun ast:g-test-corner-adjustments (/ incoming outgoing settings corner route result reversed-result adjustment angle outside nominal short-outgoing short-incoming expected)
  (setq incoming '((kind . line) (a -38.0 258.0) (b 107.80342046542515 215.04231639645309))
        outgoing '((kind . line) (a 107.80342046542515 215.04231639645309) (b 285.06457440910435 231.24365283994626))
        settings '((pitch . 3.0)) corner (ast:g-corner incoming outgoing settings)
        adjustment (car (ast:g-get 'corner-adjustments corner nil)))
  (ast:g-test (and (ast:g-get 'ok corner nil) (= 1 (length (ast:g-get 'corner-adjustments corner nil)))
    (equal 3.097120227 (ast:g-get 'distance adjustment 0.0) 1e-7)
    (equal '(107.80342046542515 215.04231639645309) (ast:g-get 'center adjustment nil) 1e-8))
    "Shallow user corner uses the smallest allowed construction adjustment at the guide vertex")
  (ast:g-test (not (ast:g-get 'ok (ast:g-corner incoming outgoing '((pitch . 3.0) (corrections . nil))) nil))
    "Disabling adjustments preserves nominal-only corner rejection")
  (setq route (list (cons 'primitives (list incoming outgoing))) result (ast:g-solve route settings nil)
        reversed-result (ast:g-solve route '((pitch . 3.0) (reverse . T)) nil))
  (ast:g-test (and (ast:g-get 'ok result nil) (= 'adjusted (ast:g-get 'status result nil))
    (= 1 (length (ast:g-get 'corner-adjustments result nil)))
    (= 1 (length (vl-remove-if-not '(lambda (item)
      (< (ast:g-dist (ast:g-get 'center item nil) (ast:g-get 'a outgoing nil)) 1e-8)) (ast:g-get 'openings result nil)))))
    "Shallow user route fits with one marked corner adjustment and one vertex slit")
  (ast:g-test (and (ast:g-get 'ok reversed-result nil)
    (= (length (ast:g-get 'openings result nil)) (length (ast:g-get 'openings reversed-result nil)))
    (equal (ast:g-get 'center adjustment nil)
      (ast:g-get 'center (car (ast:g-get 'corner-adjustments reversed-result nil)) nil) 1e-8)
    (equal (ast:g-get 'virtual-center adjustment nil)
      (ast:g-get 'virtual-center (car (ast:g-get 'corner-adjustments reversed-result nil)) nil) 1e-8))
    "Reversing the adjusted shallow corner preserves its adjusted physical slit and virtual centre")
  (setq angle (* 2.0 (atan (/ (* 0.75 (sin (* pi (/ 40.0 180.0))))
    (- 3.3 (* 0.75 (cos (* pi (/ 40.0 180.0)))))))))
  (foreach outside '(nil T)
    (setq corner (ast:g-corner (ast:g-test-guide 0.0 1 0.0 30.0 T)
      (ast:g-test-guide 0.0 1 (+ angle (if outside -1e-5 1e-5)) 30.0 nil) settings))
    (ast:g-test (if outside (not (ast:g-get 'ok corner nil))
      (and (ast:g-get 'ok corner nil)
        (<= (ast:g-get 'distance (car (ast:g-get 'corner-adjustments corner nil)) 0.0) 3.3)))
      (if outside "Corner requiring more than ten percent adjustment is rejected"
        "Corner just inside ten percent adjustment is accepted")))
  (setq incoming (ast:g-test-guide 0.0 1 0.0 30.0 T)
        outgoing (ast:g-test-guide 8.0 1 (/ pi 2.0) (* 8.0 (/ pi 3.0)) nil)
        nominal (ast:g-corner incoming outgoing settings))
  (ast:g-test (and (ast:g-get 'ok nominal nil) (null (ast:g-get 'corner-adjustments nominal nil)))
    "Feasible nominal corner construction is not adjusted")
  (setq short-outgoing (ast:g-test-guide 8.0 1 (/ pi 2.0) (- (ast:g-get 'outgoing-station nominal 0.0) 0.05) nil)
        short-incoming (ast:g-test-guide 0.0 1 0.0 (- 30.0 (ast:g-get 'incoming-station nominal 0.0)) T)
        corner (ast:g-corner short-incoming short-outgoing settings)
        adjustment (car (ast:g-get 'corner-adjustments corner nil))
        expected (* 16.0 (sin (/ (- (ast:g-test-chord-station 8.0 3.0) 0.05) 16.0))))
  (ast:g-test (and (ast:g-get 'ok corner nil) (equal expected (ast:g-get 'distance adjustment 0.0) 1e-8)
    (> (ast:g-get 'distance adjustment 0.0) 2.7)
    (equal (ast:g-get 'opening nominal nil) (ast:g-get 'opening corner nil) 1e-8))
    "Curved corner contracts its direct construction chord without moving the virtual-tip hole")
  (setq result (ast:g-solve (list (cons 'primitives (list short-incoming short-outgoing))) settings nil))
  (ast:g-test (and (ast:g-get 'ok result nil) (= 3 (length (ast:g-get 'openings result nil)))
    (= 2 (length (ast:g-get 'intervals result nil))) (= 1 (length (ast:g-get 'corner-adjustments result nil))))
    "Adjusted corner at finite arm ends keeps three openings without duplicate zero-span slits"))

(defun ast:g-test-shallow-curves (/ fixture radius-in sigma-in radius-out sigma-out degrees required angle incoming outgoing settings corner expected-ok label q-in q-out station-in station-out before after virtual-in virtual-out joint result)
  ;; Required chords come from independent line/circle tip-locus intersections.
  ;; Both turn signs and all curvature senses include nominal, adjusted and over-limit cases.
  (setq settings '((pitch . 3.0) (thickness . 0.2) (margin . 0.2)))
  (foreach fixture '((0.0 1 100.0 -1 -21.5 3.035647595) (0.0 1 100.0 -1 21.5 3.026578361)
                    (0.0 1 100.0 1 -21.5 3.203569803) (0.0 1 100.0 1 21.5 3.212927180)
                    (100.0 -1 0.0 1 -21.5 3.212927180) (100.0 -1 0.0 1 21.5 3.203569803)
                    (100.0 1 0.0 1 -21.5 3.026578361) (100.0 1 0.0 1 21.5 3.035647595)
                    (100.0 -1 80.0 -1 -21.5 3.102605413) (100.0 -1 80.0 -1 21.5 3.081977019)
                    (100.0 -1 80.0 1 -21.5 3.347357177) (100.0 -1 80.0 1 21.5 3.349753725)
                    (100.0 1 80.0 -1 -21.5 2.941570546) (100.0 1 80.0 -1 21.5 2.939340134)
                    (100.0 1 80.0 1 -21.5 3.125961461) (100.0 1 80.0 1 21.5 3.146751067))
    (setq radius-in (nth 0 fixture) sigma-in (nth 1 fixture) radius-out (nth 2 fixture)
          sigma-out (nth 3 fixture) degrees (nth 4 fixture) required (nth 5 fixture)
          angle (* pi (/ degrees 180.0)) expected-ok (<= required 3.3)
          incoming (ast:g-test-guide radius-in sigma-in 0.0 30.0 T)
          outgoing (ast:g-test-guide radius-out sigma-out angle 30.0 nil)
          corner (ast:g-corner incoming outgoing settings)
          label (strcat "shallow curve " (vl-princ-to-string fixture)))
    (ast:g-test (equal (if (ast:g-get 'ok corner nil) T nil) expected-ok)
      (strcat label " independently bounded feasibility"))
    (if (and expected-ok (ast:g-get 'ok corner nil))
      (progn
        (setq q-in (if (< degrees 0.0) (max 3.0 required) 3.0)
              q-out (if (> degrees 0.0) (max 3.0 required) 3.0)
              station-in (- (ast:g-get 'incoming-station corner 0.0) 30.0)
              station-out (ast:g-get 'outgoing-station corner 0.0)
              before (ast:g-test-corner-slit radius-in sigma-in 0.0 station-in)
              after (ast:g-test-corner-slit radius-out sigma-out angle station-out)
              virtual-in (ast:g-test-corner-slit radius-in sigma-in 0.0
                (+ station-in (ast:g-test-chord-station radius-in q-in)))
              virtual-out (ast:g-test-corner-slit radius-out sigma-out angle
                (- station-out (ast:g-test-chord-station radius-out q-out)))
              joint (ast:g-get 'center (ast:g-get 'opening corner nil) nil))
        (ast:g-test (and (>= station-in -30.0) (<= station-in 1e-8)
                         (>= station-out -1e-8) (<= station-out 30.0))
          (strcat label " real neighbours stay on finite arms"))
        (ast:g-test (and (equal (distance (car before) (car virtual-in)) q-in 1e-8)
                         (equal (distance (car after) (car virtual-out)) q-out 1e-8)
                         (>= q-in 2.7) (<= q-in 3.3) (>= q-out 2.7) (<= q-out 3.3))
          (strcat label " independent direct construction chords stay within allowance"))
        (ast:g-test (and
          (equal joint (mapcar '- (car virtual-in) (mapcar '(lambda (value) (* 0.75 value)) (cadr virtual-in))) 1e-8)
          (equal joint (mapcar '+ (car virtual-out) (mapcar '(lambda (value) (* 0.75 value)) (cadr virtual-out))) 1e-8))
          (strcat label " adjusted neighbours reconstruct the fixed selected-tip hole"))
        (ast:g-test (= (length (ast:g-get 'corner-adjustments corner nil)) (if (> required 3.0) 1 0))
          (strcat label " nominal-first policy marks only the arm that needs adjustment"))
        (setq result (ast:g-solve (list (cons 'primitives (list incoming outgoing))) settings nil))
        (ast:g-test (and (ast:g-get 'ok result nil)
          (= (length (ast:g-get 'corner-adjustments result nil)) (if (> required 3.0) 1 0)))
          (strcat label " complete finite route fits with the expected corner adjustment")))))
  (setq corner (ast:g-corner (ast:g-test-guide 0.0 1 0.0 4.0 T)
    (ast:g-test-guide 100.0 1 (* pi (/ 21.5 180.0)) 30.0 nil) settings))
  (ast:g-test (and (not (ast:g-get 'ok corner nil)) (wcmatch (ast:g-get 'error corner "") "A guide is too short*"))
    "Shallow line-to-arc corner rejects an incoming arm shorter than the minimum construction step")
  (setq corner (ast:g-corner (ast:g-test-guide 100.0 1 0.0 30.0 T)
    (ast:g-test-guide 0.0 1 (* pi (/ -21.5 180.0)) 4.0 nil) settings))
  (ast:g-test (and (not (ast:g-get 'ok corner nil)) (wcmatch (ast:g-get 'error corner "") "A guide is too short*"))
    "Shallow arc-to-line corner rejects an outgoing arm shorter than the minimum construction step")
  ;; Independent R8, +90-degree intersection gives c_o=-1.1220523187783322;
  ;; adding the advance for chord2.7 gives this minimum finite arc length.
  (setq corner (ast:g-corner (ast:g-test-guide 0.0 1 0.0 30.0 T)
    (ast:g-test-guide 8.0 1 (/ pi 2.0) (+ 1.59092918307259 1e-5) nil) settings))
  (ast:g-test (and (ast:g-get 'ok corner nil)
    (>= (ast:g-get 'distance (car (ast:g-get 'corner-adjustments corner nil)) 0.0) 2.7)
    (< (ast:g-get 'distance (car (ast:g-get 'corner-adjustments corner nil)) 0.0) 2.7001))
    "Curved construction just above the ten-percent contraction boundary remains feasible")
  (setq corner (ast:g-corner (ast:g-test-guide 0.0 1 0.0 30.0 T)
    (ast:g-test-guide 8.0 1 (/ pi 2.0) (- 1.59092918307259 1e-5) nil) settings))
  (ast:g-test (and (not (ast:g-get 'ok corner nil)) (wcmatch (ast:g-get 'error corner "") "A guide is too short*"))
    "Curved construction beyond the ten-percent contraction boundary is rejected")
  ;; Even q=3.3 gives less than 2.36 mm slit-axis-to-hole clearance on the straight arm;
  ;; this profile requires 3.35 mm. Allowing finite-arm adjustment cannot make it safe.
  (setq corner (ast:g-corner (ast:g-test-guide 0.0 1 0.0 30.0 T)
    (ast:g-test-guide 100.0 1 (* pi (/ 21.5 180.0)) 30.0 nil)
    '((pitch . 3.0) (thickness . 0.2) (margin . 3.0))))
  (ast:g-test (and (not (ast:g-get 'ok corner nil)) (wcmatch (ast:g-get 'error corner "") "Two stitch holes*"))
    "Shallow curved corner still refuses a clearance margin larger than any allowed construction can provide"))

(defun ast:g-tests (/ ast:g-test-count ast:g-test-failures result route settings original split incoming outgoing corner sigma-in sigma-out turn opening virtual-before virtual-after root first-cut other-cut width-settings)
  (setq ast:g-test-count 0 ast:g-test-failures nil)
  (ast:g-test-corner-matrix)
  (ast:g-test-corner-adjustments)
  (ast:g-test-shallow-curves)
  (setq result (ast:g-test-corner-transforms)
        ast:g-test-count (+ ast:g-test-count (ast:g-get 'checks result 0))
        ast:g-test-failures (append (reverse (ast:g-get 'failures result nil)) ast:g-test-failures))
  (setq route '((kind . line) (a 0.0 0.0) (b 30.0 0.0)))
  (setq result (ast:g-solve-primitive route '((pitch . 3.0)) nil 1.0 (+ 1.0 1e-15)))
  (ast:g-test (and (ast:g-get 'ok result nil) (= 1 (length (ast:g-get 'openings result nil)))
                   (null (ast:g-get 'intervals result nil))
                   (equal '(1.0 0.0) (ast:g-get 'center (car (ast:g-get 'openings result nil)) nil) 1e-14))
              "arithmetic-near anchors reuse one opening without interval")
  (setq result (ast:g-solve-primitive route '((pitch . 3.0)) nil 1.0 (+ 1.0 1e-8)))
  (ast:g-test (and (not (ast:g-get 'ok result nil)) (wcmatch (ast:g-get 'error result "") "Stitches cannot fit*"))
              "genuinely positive 1e-8 span is not collapsed into one opening")
  (setq result (ast:g-solve-primitive '((kind . line) (a 1000.0 1000.0) (b 1030.0 1000.0))
                                     '((pitch . 3.0)) nil 1.0 (+ 1.0 1e-8)))
  (ast:g-test (and (not (ast:g-get 'ok result nil)) (wcmatch (ast:g-get 'error result "") "Stitches cannot fit*"))
              "translated genuinely positive 1e-8 span still rejects at world offset1000")
  (setq result (ast:g-solve (list (cons 'primitives (list route))) '((pitch . 3.0))
                            '(((primitive . 0) (station . 10.1)) ((primitive . 0) (station . 13.1)))))
  (ast:g-test (and (ast:g-get 'ok result nil)
                   (= 1 (length (vl-remove-if-not '(lambda (item) (equal (ast:g-get 'center item nil) '(11.6 0.0) 1e-8)) (ast:g-get 'openings result nil))))
                   (= 2 (length (vl-remove-if-not '(lambda (item) (and (ast:g-get 'reserved item nil) (equal (ast:g-get 'distance item 0.0) 3.0 1e-8))) (ast:g-get 'intervals result nil))))
                   (= (length (ast:g-get 'intervals result nil)) (1- (length (ast:g-get 'openings result nil)))))
              "adjacent landmark gaps share one opening and both retain nominal pitch")
  (setq result (ast:g-fit-line 30.5 3.0 0 0 T))
  (ast:g-test (and (= (cdr (assoc 'count result)) 10) (= (cdr (assoc 'changed result)) 2) (= (cdr (assoc 'block-start result)) 4)) "30.5 central two gaps")
  (setq result (ast:g-fit-line 31.5 3.0 0 0 T))
  (ast:g-test (and (= (cdr (assoc 'count result)) 11) (= (cdr (assoc 'changed result)) 5) (= (cdr (assoc 'block-start result)) 3)) "31.5 symmetric count tie")
  (setq result (ast:g-fit-line 30.3 3.0 0 0 T))
  (ast:g-test (= (cdr (assoc 'block-start result)) 5) "half index tie toward end")
  (setq result (ast:g-fit-line 6.3 3.0 0 1 T))
  (ast:g-test (equal (cdr (assoc 'gaps result)) '(3.3 3.0) 1e-8) "protected final gap")
  (ast:g-test (not (cdr (assoc 'ok (ast:g-fit-line 7.0 3.0 0 0 T)))) "infeasible seven")
  (ast:g-test (not (cdr (assoc 'ok (ast:g-fit-line 30.5 3.0 0 0 nil)))) "disabled corrections")
  (setq route '((primitives ((kind . line) (a 0.0 0.0) (b 30.0 0.0)))) settings '((pitch . 3.0)))
  (setq result (ast:g-solve route settings nil))
  (ast:g-test (and (cdr (assoc 'ok result)) (= (length (cdr (assoc 'openings result))) 11)) "line eleven openings")
  (setq result (ast:g-solve route settings '(((primitive . 0) (station . 16.5)))))
  (ast:g-test (and (cdr (assoc 'ok result)) (= (length (cdr (assoc 'openings result))) 11)) "landmark centred nominal gap")
  (setq result (ast:g-solve route '((pitch . 3.0) (slit-length . 3.0) (thickness . 0.2) (margin . 0.2)) nil))
  (ast:g-test (cdr (assoc 'ok result)) "finite footprint replaces length-only guard")
  (setq result (ast:g-fit-arc 10.0 (/ pi 2.0) 3.0 0 0 T))
  (ast:g-test (cdr (assoc 'ok result)) "quarter circle chord fit")
  (setq original (ast:g-solve route settings nil)
        split '((primitives ((kind . line) (a 0.0 0.0) (b 11.0 0.0)) ((kind . line) (a 11.0 0.0) (b 30.0 0.0))))
        result (ast:g-solve split settings nil))
  (ast:g-test (equal (ast:g-get 'openings result nil) (ast:g-get 'openings original nil) 1e-8) "redundant line vertex normalized")
  (setq result (ast:g-solve route '((pitch . 3.0) (reverse . T)) '(((primitive . 0) (station . 16.5)))))
  (ast:g-test (and (ast:g-get 'ok result nil) (equal (ast:g-get 'center (car (ast:g-get 'openings result nil)) nil) '(30.0 0.0) 1e-8)) "reverse with fixed native landmark")
  (setq incoming '((kind . line) (a -30.0 0.0) (b 0.0 0.0)) outgoing '((kind . line) (a 0.0 0.0) (b 0.0 -30.0)))
  (setq corner (ast:g-corner incoming outgoing settings))
  (ast:g-test (ast:g-get 'ok corner nil) "sharp ninety degree line corner")
  (setq route (list (cons 'primitives (list incoming outgoing))) result (ast:g-solve route settings nil))
  (ast:g-test (and (ast:g-get 'ok result nil) (= 1 (length (vl-remove-if-not '(lambda (item) (= (ast:g-get 'type item nil) 'round)) (ast:g-get 'openings result nil))))) "ordered sharp route emits one round hole")
  (ast:g-test (= (length (ast:g-get 'intervals result nil)) (1- (length (ast:g-get 'openings result nil)))) "open sharp route interval identity")
  (setq route (list (cons 'primitives (list (list '(kind . arc) '(center 0.0 0.0) '(radius . 10.0) '(start-angle . 0.0) (cons 'sweep (* 2.0 pi))))) '(closed . T))
        result (ast:g-solve route settings nil))
  (ast:g-test (and (ast:g-get 'ok result nil) (= (length (ast:g-get 'openings result nil)) (length (ast:g-get 'intervals result nil)))) "circle closure reuses first identity")
  (setq result (ast:g-solve route '((pitch . 3.0) (phase . 5.0)) nil))
  (ast:g-test (equal (ast:g-get 'center (car (ast:g-get 'openings result nil)) nil) (list (* 10.0 (cos 0.5)) (* 10.0 (sin 0.5))) 1e-8) "circle picked phase")
  (setq route '((primitives ((kind . line) (a 0.0 0.0) (b 40.0 0.0)))) result (ast:g-solve route '((pitch . 3.0) (start . 4.0) (end . 34.0)) nil))
  (ast:g-test (and (ast:g-get 'ok result nil) (= (length (ast:g-get 'openings result nil)) 11) (equal (ast:g-get 'center (car (ast:g-get 'openings result nil)) nil) '(4.0 0.0) 1e-8)) "native start end trim")
  (setq route '((primitives ((kind . line) (a 0.0 0.0) (b 30.0 30.0)) ((kind . line) (a 30.0 30.0) (b 0.0 30.0)) ((kind . line) (a 0.0 30.0) (b 30.0 0.0)))))
  (ast:g-test (not (ast:g-get 'ok (ast:g-solve route settings nil) nil)) "self crossing rejected")
  (setq incoming (list '(kind . arc) '(center 0.0 -10.0) '(radius . 10.0) (cons 'start-angle (+ (/ pi 2.0) (/ pi 3.0))) (cons 'sweep (- (/ pi 3.0))))
        outgoing '((kind . line) (a 0.0 0.0) (b 0.0 -30.0)) corner (ast:g-corner incoming outgoing settings))
  (ast:g-test (and (ast:g-get 'ok corner nil) (equal (ast:g-get 'center (ast:g-get 'opening corner nil) nil) '(0.482090909 -0.476960588) 1e-6)) "A03 reflected independent tip locus fixture")
  (foreach turn (list (/ pi 2.0) (- (/ pi 2.0)))
    (foreach sigma-in '(-1 1)
      (foreach sigma-out '(-1 1)
        (setq incoming (ast:g-test-guide 10.0 sigma-in 0.0 (* 10.0 (/ pi 3.0)) T)
              outgoing (ast:g-test-guide 8.0 sigma-out turn (* 8.0 (/ pi 3.0)) nil)
              corner (ast:g-corner incoming outgoing '((pitch . 3.0) (thickness . 0.2) (margin . 0.2))))
        (ast:g-test (ast:g-get 'ok corner nil) "arc arc local corner winding and turn matrix")
        (if (ast:g-get 'ok corner nil)
          (progn
            (setq opening (ast:g-get 'opening corner nil)
                  virtual-before (ast:g-slit incoming (+ (ast:g-get 'incoming-station corner 0) (ast:g-step incoming 3.0)) settings)
                  virtual-after (ast:g-slit outgoing (- (ast:g-get 'outgoing-station corner 0) (ast:g-step outgoing 3.0)) settings))
            (ast:g-test (and (< (ast:g-dist (ast:g-get 'center opening nil) (car (ast:g-ends virtual-before))) 1e-8)
                             (< (ast:g-dist (ast:g-get 'center opening nil) (cadr (ast:g-ends virtual-after))) 1e-8)) "arc arc recovered virtual tips agree"))))))
  (setq incoming (ast:g-test-guide 10.0 1 0.0 44.32347102828625 T)
        outgoing (ast:g-test-guide 10.0 1 (- (* pi (/ 10.0 180.0))) 32.60249587165397 nil)
        corner (ast:g-corner incoming outgoing '((pitch . 3.0) (thickness . 0.2) (margin . 0.2))))
  (ast:g-test (not (ast:g-get 'ok corner nil)) "inadmissible nearest root never replaced by farther root")
  (setq incoming (ast:g-test-guide 10.0 1 0.0 62.619976480340476 T)
        outgoing (ast:g-test-guide 10.0 1 (- (* pi (/ 10.0 180.0))) 11.39841693460145 nil)
        corner (ast:g-corner incoming outgoing '((pitch . 3.0) (thickness . 0.2) (margin . 0.2))))
  (ast:g-test (not (ast:g-get 'ok corner nil)) "principal root never rescued by extra revolution")
  (setq incoming (ast:g-test-guide 0.0 0 0.0 30.0 T) outgoing (ast:g-test-guide 10.0 1 0.0 (* 10.0 (/ pi 2.0)) nil)
        route (list (cons 'primitives (list incoming outgoing))) result (ast:g-solve route settings nil))
  (ast:g-test (and (ast:g-get 'ok result nil) (= 1 (length (vl-remove-if-not '(lambda (item) (< (ast:g-dist (ast:g-get 'center item nil) '(0.0 0.0)) 1e-8)) (ast:g-get 'openings result nil))))) "smooth curvature join shares exactly one slit")
  (setq result (ast:g-solve route settings '(((primitive . 1) (station . 0.5)))))
  (ast:g-test (not (ast:g-get 'ok result nil)) "landmark straddling curvature join rejected")
  (setq route '((primitives ((kind . line) (a 0.0 0.0) (b 30.0 0.0)) ((kind . line) (a 30.0 0.0) (b 30.0 30.0)) ((kind . line) (a 30.0 30.0) (b 0.0 30.0)) ((kind . line) (a 0.0 30.0) (b 0.0 0.0))) (closed . T))
        result (ast:g-solve route settings nil))
  (ast:g-test (and (ast:g-get 'ok result nil) (= 4 (length (vl-remove-if-not '(lambda (item) (= (ast:g-get 'type item nil) 'round)) (ast:g-get 'openings result nil))))) "closed polygon has four unique sharp holes")
  (ast:g-test (= (length (ast:g-get 'intervals result nil)) (length (ast:g-get 'openings result nil))) "closed sharp route interval identity")
  (setq result (ast:g-solve route '((pitch . 3.0) (phase . 15.0)) nil))
  (ast:g-test (and (ast:g-get 'ok result nil) (equal (ast:g-get 'center (car (ast:g-get 'openings result nil)) nil) '(15.0 0.0) 1e-8)) "closed multi primitive phase cuts original edge")
  (setq route '((primitives ((kind . line) (a 0.0 0.0) (b 30.0 0.0)) ((kind . line) (a 30.0 0.0) (b 30.0 30.0))))
        result (ast:g-solve route '((pitch . 3.0) (start . 5.0) (end . 55.0)) nil))
  (ast:g-test (and (ast:g-get 'ok result nil) (equal (ast:g-get 'center (car (ast:g-get 'openings result nil)) nil) '(5.0 0.0) 1e-8)
                   (equal (ast:g-get 'center (last (ast:g-get 'openings result nil)) nil) '(30.0 25.0) 1e-8)) "multi primitive global start end trim")
  (setq first-cut '((type . slit) (center 0.0 0.0) (axis 1.0 0.0) (length . 2.0))
        other-cut '((type . slit) (center 3.0 0.0) (axis 1.0 0.0) (length . 2.0)) width-settings '((thickness . 0.2) (margin . 0.0)))
  (ast:g-test (and (ast:g-box-separated (ast:g-opening-box first-cut 0.2) (ast:g-opening-box other-cut 0.2) 0.0)
                   (null (ast:g-validate-openings (list first-cut other-cut) width-settings))) "separated capsule boxes prove clearance")
  (setq other-cut '((type . slit) (center 2.2 0.0) (axis 1.0 0.0) (length . 2.0)))
  (ast:g-test (and (not (ast:g-box-separated (ast:g-opening-box first-cut 0.2) (ast:g-opening-box other-cut 0.2) 0.0))
                   (ast:g-validate-openings (list first-cut other-cut) width-settings)) "touching capsule boxes retain exact contact rejection")
  (setq other-cut '((type . slit) (center 2.0000000001 0.0) (axis 1.0 0.0) (length . 2.0)))
  (ast:g-test (ast:g-validate-openings (list first-cut other-cut) nil) "box prefilter preserves near contact arithmetic rejection")
  (setq other-cut '((type . slit) (center 0.0 0.0) (axis 0.0 1.0) (length . 2.0)))
  (ast:g-test (ast:g-validate-openings (list first-cut other-cut) width-settings) "crossing axes never skipped by boxes")
  (setq other-cut '((type . round) (center 1.6 0.0) (diameter . 1.0)))
  (ast:g-test (and (not (ast:g-box-separated (ast:g-opening-box first-cut 0.2) (ast:g-opening-box other-cut 0.2) 0.0))
                   (ast:g-validate-openings (list first-cut other-cut) width-settings)) "disk capsule touching remains rejected")
  (setq other-cut '((type . slit) (center 2.4 0.0) (axis 1.0 0.0) (length . 2.0)))
  (ast:g-test (and (not (ast:g-box-separated (ast:g-opening-box first-cut 0.2) (ast:g-opening-box other-cut 0.2) 0.2))
                   (null (ast:g-validate-openings (list first-cut other-cut) '((thickness . 0.2) (margin . 0.2))))) "exact positive margin uses exact accepted distance")
  (setq first-cut '((type . round) (center 0.0 0.0) (diameter . 1.0)) other-cut '((type . round) (center 1.0 0.0) (diameter . 1.0)))
  (ast:g-test (ast:g-validate-openings (list first-cut other-cut) nil) "touching disk boxes retain exact rejection")
  (setq result (ast:g-fit-line 6300.0 3.0 0 0 T))
  (ast:g-test (and (not (ast:g-get 'ok result nil)) (wcmatch (ast:g-get 'error result "") "*2000*")) "selected fit above bounded interval limit refuses")
  (setq route '((primitives ((kind . line) (a 0.0 0.0) (b 6000.0 0.0)))) result (ast:g-solve route nil nil))
  (ast:g-test (and (not (ast:g-get 'ok result nil)) (wcmatch (ast:g-get 'error result "") "*2000 holes*")) "2001 opening seam explicitly refuses without truncation")
  (setq route '((primitives ((kind . line) (a 0.0 0.0) (b 5997.0 0.0)))) result (ast:g-solve route nil nil))
  (ast:g-test (and (ast:g-get 'ok result nil) (= 2000 (length (ast:g-get 'openings result nil)))) "2000 opening inclusive seam limit")
  (ast:g-test-stitch-hand)
  (list (cons 'ok (null ast:g-test-failures)) (cons 'checks ast:g-test-count) (cons 'failures (reverse ast:g-test-failures))))
(princ)
