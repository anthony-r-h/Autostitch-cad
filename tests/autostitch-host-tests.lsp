;;; Run only in a disposable test drawing; these tests create and copy entities.
(defun ast:host-tests (/ ast:*cad-test-passed* ast:*cad-test-failures* original-units original-copy original-tile settings guide output result selection before cursor copied-guide copied-output original-name data paper-guide document)
  (setq ast:*cad-test-passed* 0 ast:*cad-test-failures* nil
        original-units (getvar "INSUNITS") original-copy (getvar "COPYMODE") original-tile (getvar "TILEMODE")
        document (vla-get-ActiveDocument (vlax-get-acad-object)) settings (ast:cad-default-settings))
  (setvar "INSUNITS" 4) (setvar "COPYMODE" 1) (setvar "TILEMODE" 1)
  (setq guide (entmakex '((0 . "LINE") (8 . "0") (10 0.0 300.0 0.0) (11 30.0 300.0 0.0)))
        result (ast:cad-generate guide settings nil) output (ast:cad-get 'output result)
        original-name (cdr (assoc 2 (entget output))) selection (ssadd guide))
  (ssadd output selection)
  (setq before (entlast))
  (vl-cmdf "_.COPY" selection "" "_non" '(0.0 0.0 0.0) "_non" '(60.0 0.0 0.0))
  (setq cursor (entnext before))
  (while cursor
    (cond ((= "LINE" (cdr (assoc 0 (entget cursor)))) (setq copied-guide cursor))
          ((= "INSERT" (cdr (assoc 0 (entget cursor)))) (setq copied-output cursor)))
    (setq cursor (entnext cursor)))
  (ast:cad-test-assert (and copied-guide copied-output
    (equal copied-output (ast:cad-get 'output (ast:cad-read copied-guide)))
    (equal copied-guide (ast:cad-get 'guide (ast:cad-read copied-output))))
    "Native COPY both remaps reciprocal references")
  (ast:cad-test-assert (and (ast:cad-get 'common-placement (ast:cad-read copied-guide))
    (not (ast:cad-get 'stale (ast:cad-read copied-guide)))) "Copied pair translation remains current")
  (setq result (ast:cad-generate copied-guide settings nil))
  (ast:cad-test-assert (and (ast:cad-get 'ok result)
    (equal original-name (cdr (assoc 2 (entget output))))
    (/= original-name (cdr (assoc 2 (entget copied-output))))) "Copied pair regenerates independently")
  (setq guide (entmakex '((0 . "LINE") (8 . "0") (10 0.0 350.0 0.0) (11 30.0 350.0 0.0))))
  (setvar "TILEMODE" 0)
  (setq result (ast:cad-generate guide settings nil) output (ast:cad-get 'output result))
  (ast:cad-test-assert (and (ast:cad-get 'ok result)
    (equal (cdr (assoc 330 (entget guide))) (cdr (assoc 330 (entget output)))))
    "Model guide creates model output while paper space is active")
  (setq paper-guide (vlax-vla-object->ename (vla-AddLine (vla-get-PaperSpace document)
    (vlax-3d-point '(10.0 10.0 0.0)) (vlax-3d-point '(40.0 10.0 0.0)))))
  (setvar "TILEMODE" 1)
  (setq result (ast:cad-generate paper-guide settings nil) output (ast:cad-get 'output result))
  (ast:cad-test-assert (and (ast:cad-get 'ok result)
    (equal (cdr (assoc 330 (entget paper-guide))) (cdr (assoc 330 (entget output)))))
    "Paper guide creates paper output while model space is active")
  (setvar "INSUNITS" original-units) (setvar "COPYMODE" original-copy) (setvar "TILEMODE" original-tile)
  (list (cons 'passed ast:*cad-test-passed*) (cons 'failed (length ast:*cad-test-failures*))
        (cons 'failures (reverse ast:*cad-test-failures*))))
(princ)

;;; Run separately after loading the current UI and compiled palette.
(defun ast:ui-test-enabled-p (control)
  (member (dcl-Control-GetProperty "AUTOSTITCH" "Palette" control "Enabled") '(T 1 -1)))

(defun ast:ui-test-matching-registration (/ fixture result circle state)
  (foreach fixture '((((reverse . nil)) 0.0 nil "Full guide start selects forward correspondence")
                     (((reverse . nil)) 100.0 T "Full guide opposite start selects reversed correspondence")
                     (((reverse . T)) 100.0 nil "Reversed travel uses the full guide end as S")
                     (((reverse . T)) 0.0 T "Reversed travel maps S to the other native endpoint")
                     (((start . 80.0) (end . 95.0)) 80.0 nil "Trimmed start beyond midpoint keeps corresponding target range")
                     (((start . 80.0) (end . 95.0)) 20.0 T "Trimmed start identifies the mirrored target range")
                     (((start . 5.0) (end . 20.0) (reverse . T)) 20.0 nil "Reversed trimmed travel uses saved end as S")
                     (((start . 5.0) (end . 20.0) (reverse . T)) 80.0 T "Reversed trimmed S identifies opposite target traversal"))
    (setq result (ast:ui-match-direction (car fixture) 100.0 100.0 (cadr fixture)))
    (ast:cad-test-assert (and result (equal (ast:cad-get 'reversed result) (caddr fixture))) (cadddr fixture)))
  (ast:cad-test-assert (and (null (ast:ui-match-direction '((start . 50.0)) 100.0 100.0 50.0))
    (null (ast:ui-match-direction '((start . 80.0)) 100.0 100.0 50.0)))
    "Equidistant matching picks require a direction instead of silently choosing one")
  (foreach fixture '((nil 100.0 nil "Heading toward native end resolves forward travel")
                     (nil 0.0 T "Heading toward native start resolves reversed travel")
                     (T 100.0 T "Reversed source travel resolves target forward direction")
                     (T 0.0 nil "Reversed source travel resolves target backward direction"))
    (setq result (ast:ui-match-toward (list (cons 'reverse (car fixture))) 100.0 (cadr fixture)))
    (ast:cad-test-assert (and result (equal (ast:cad-get 'reversed result) (caddr fixture))) (cadddr fixture)))
  (ast:cad-test-assert (null (ast:ui-match-toward nil 100.0 50.0))
    "A second midpoint pick remains unresolved and cannot become a valid forward registration")
  (setq circle (entmakex '((0 . "CIRCLE") (8 . "0") (10 100.0 1840.0 0.0) (40 . 10.0)))
        state (ast:cad-read circle))
  (ast:cad-test-assert (equal (ast:ui-match-station state '(100.0 1850.0 0.0)) (* 5.0 pi) 1e-8)
    "Exact loop start point projects to its arc-length phase")
  (ast:cad-test-assert (equal (ast:ui-match-station (ast:cad-put 'factor 25.4 state) '(100.0 1850.0 0.0)) (* 127.0 pi) 1e-8)
    "Matching start projection converts drawing units to millimetres")
  (entdel circle))

(defun ast:ui-test-matching (/ settings source target first second result source-output target-output source-record target-record target-data)
  (setq settings (ast:cad-default-settings)
        source (entmakex '((0 . "LINE") (8 . "0") (10 0.0 1850.0 0.0) (11 30.0 1850.0 0.0)))
        target (entmakex '((0 . "LINE") (8 . "0") (10 50.0 1850.0 0.0) (11 80.0 1850.0 0.0))))
  (ast:ui-adopt (ast:cad-read source))
  (ast:cad-test-assert (and (ast:ui-test-enabled-p "Face") (ast:ui-test-enabled-p "Match")
    (not (ast:ui-test-enabled-p "Unmatch"))
    (= "Match guide" (dcl-Control-GetProperty "AUTOSTITCH" "Palette" "Match" "Caption"))
    (= "" (dcl-Control-GetProperty "AUTOSTITCH" "Palette" "MatchingInfo" "Caption")))
    "An independent guide offers face and link actions without claiming a matching source")
  (ast:ui-put "Pitch" "Text" "3.4")
  (c:ASTUIFACE 1 "Back face")
  (ast:cad-test-assert (and
    (= "3.4" (dcl-Control-GetProperty "AUTOSTITCH" "Palette" "Pitch" "Text"))
    (= -1 (ast:cad-get 'face (ast:match-info source)))
    (equal 3.0 (ast:cad-get 'pitch (ast:cad-get 'settings (ast:cad-read source))) 1e-10)
    (= 1 (dcl-ComboBox-GetCurSel "AUTOSTITCH" "Palette" "Face")))
    "Changing face preserves the unsaved pitch text without saving it as the source pitch")
  (c:ASTUISTITCH 1 "Reverse")
  (ast:cad-test-assert (and (ast:ui-test-enabled-p "Stitch")
    (= "3.4" (dcl-Control-GetProperty "AUTOSTITCH" "Palette" "Pitch" "Text"))
    (= -1 (ast:cad-get 'face (ast:match-info source)))
    (= -1 (ast:cad-get 'stitch-hand (ast:cad-get 'settings (ast:cad-read source))))
    (not (ast:cad-get 'reverse (ast:cad-get 'settings (ast:cad-read source))))
    (= 1 (dcl-ComboBox-GetCurSel "AUTOSTITCH" "Palette" "Stitch")))
    "The palette changes stitch lean independently of face travel and the unsaved pitch draft")
  (ast:ui-adopt (ast:cad-read target))
  (ast:ui-put "Pitch" "Text" "not a number")
  (setq result (ast:match-link source target -1 nil))
  (ast:cad-require (ast:cad-get 'ok result) "Could not create the matching palette fixture.")
  (ast:cad-test-assert (and (ast:ui-ready)
    (= astui:*pitch-text* (dcl-Control-GetProperty "AUTOSTITCH" "Palette" "Pitch" "Text"))
    (not (ast:ui-test-enabled-p "Pitch")))
    "An externally matched copy discards its previous editable pitch draft")
  (c:ASTUIGENERATE)
  (ast:cad-test-assert (and (ast:cad-get 'output (ast:cad-read source))
    (ast:cad-get 'output (ast:cad-read target))
    (not (ast:cad-get 'stale (ast:cad-read source)))
    (not (ast:cad-get 'stale (ast:cad-read target))))
    "Generate from the newly matched copy uses source inputs despite its earlier invalid draft")
  (ast:ui-adopt (ast:cad-read source))
  (ast:cad-test-assert (and (eq 'source (ast:cad-get 'role (ast:match-info source)))
    (vl-every 'ast:ui-test-enabled-p '("Pitch" "Start" "End" "Reverse" "Add" "Face" "Generate" "Match"))
    (not (ast:ui-test-enabled-p "Connect")) (not (ast:ui-test-enabled-p "Disconnect"))
    (= "Match guide" (dcl-Control-GetProperty "AUTOSTITCH" "Palette" "Match" "Caption"))
    (= "Source for 1 matching stitch line" (dcl-Control-GetProperty "AUTOSTITCH" "Palette" "MatchingInfo" "Caption")))
    "A matching source keeps layout editing available while connected-guide changes are disabled")
  (ast:ui-adopt (ast:cad-read target))
  (ast:cad-test-assert (and (eq 'copy (ast:cad-get 'role (ast:match-info target)))
    (not (vl-some 'ast:ui-test-enabled-p '("Pitch" "Start" "End" "Reverse" "Add" "Delete" "Landmarks" "Connect" "Disconnect")))
    (vl-every 'ast:ui-test-enabled-p '("Face" "Generate" "Match" "Unmatch"))
    (= "Select source" (dcl-Control-GetProperty "AUTOSTITCH" "Palette" "Match" "Caption"))
    (= (strcat "Uses layout from " (ast:cad-stitch-id source))
      (dcl-Control-GetProperty "AUTOSTITCH" "Palette" "MatchingInfo" "Caption")))
    "A linked copy identifies its source and disables independent layout edits while retaining face and generation actions")
  (ast:cad-test-assert (and (not (ast:ui-test-enabled-p "Stitch"))
    (= 1 (dcl-ComboBox-GetCurSel "AUTOSTITCH" "Palette" "Stitch")))
    "A matching copy displays inherited stitch lean and disables its independent selector")
  (setq source-record (ast:cad-record source) target-record (ast:cad-record target))
  (c:ASTUIMATCH)
  (ast:cad-test-assert (and (equal source astui:*guide*)
    (equal source-record (ast:cad-record source)) (equal target-record (ast:cad-record target))
    (ast:ui-test-enabled-p "Pitch")
    (= "Match guide" (dcl-Control-GetProperty "AUTOSTITCH" "Palette" "Match" "Caption")))
    "Select source on a linked copy selects its source directly without altering either guide")
  (ast:ui-adopt (ast:cad-read target))
  (c:ASTUIFACE 1 "Back face")
  (c:ASTUIGENERATE)
  (setq source-output (ast:cad-get 'output (ast:cad-read source))
        target-output (ast:cad-get 'output (ast:cad-read target)))
  (ast:cad-test-assert (and source-output target-output (not (equal source-output target-output))
    (= -1 (ast:cad-get 'face (ast:match-info target)))
    (not (ast:cad-get 'stale (ast:cad-read source))) (not (ast:cad-get 'stale (ast:cad-read target)))
    (not (ast:ui-test-enabled-p "Pitch")) (ast:ui-test-enabled-p "Unmatch"))
    "Generate from a copy applies its chosen face to a complete matching family and keeps source-controlled edits disabled")
  (setq target-data (entget target))
  (entmod (ast:cad-put 11 '(80.0 1850.0 1.0) target-data))
  (setq result (ast:cad-read source))
  (if (ast:cad-get 'ok result) (ast:ui-adopt result))
  (ast:cad-test-assert (and (ast:cad-get 'ok result) (ast:cad-get 'stale result)
    (equal source astui:*guide*) (ast:ui-test-enabled-p "Generate")
    (entget source-output) (entget target-output))
    "A child guide moved out of plane leaves its valid source selectable and both outputs intact")
  (entmod target-data)
  (entmod (ast:cad-put 10 '(7.0 3.0 0.0) (entget target-output)))
  (ast:ui-adopt (ast:cad-read source))
  (ast:cad-test-assert (and astui:*placement-conflict*
    (ast:cad-get 'placement-conflict (ast:cad-read target)))
    "The source palette detects a matching copy output moved separately from its guide")
  (c:ASTUIGENERATE)
  (ast:cad-test-assert (and (equal target-data (entget target))
    (ast:cad-placement-ok-p target-output)
    (not (ast:cad-get 'placement-conflict (ast:cad-read source)))
    (not (ast:cad-get 'stale (ast:cad-read source)))
    (not (ast:cad-get 'stale (ast:cad-read target))))
    "Generate from the source restores a moved matching output and leaves its guide unchanged")
  (ast:ui-adopt (ast:cad-read target))
  (c:ASTUIUNMATCH)
  (ast:cad-test-assert (and (not (ast:cad-get 'active (ast:match-info target)))
    (vl-every 'ast:ui-test-enabled-p '("Pitch" "Start" "End" "Reverse" "Add" "Connect" "Face" "Generate"))
    (not (ast:ui-test-enabled-p "Unmatch"))
    (= "Match guide" (dcl-Control-GetProperty "AUTOSTITCH" "Palette" "Match" "Caption"))
    (= "" (dcl-Control-GetProperty "AUTOSTITCH" "Palette" "MatchingInfo" "Caption"))
    source-output target-output (entget source-output) (entget target-output))
    "Unlink returns the selected copy to independent editing and preserves both existing stitch outputs")
  (setq first (entmakex '((0 . "LINE") (8 . "0") (10 0.0 1900.0 0.0) (11 15.0 1900.0 0.0)))
        second (entmakex '((0 . "LINE") (8 . "0") (10 15.0 1900.0 0.0) (11 30.0 1900.0 0.0)))
        result (ast:cad-connect-guides first second nil settings nil))
  (ast:cad-require (ast:cad-get 'ok result) "Could not create the connected face palette fixture.")
  (ast:ui-adopt (ast:cad-read second))
  (ast:ui-put "Pitch" "Text" "3.7")
  (c:ASTUIFACE 1 "Back face")
  (ast:cad-test-assert (and
    (= "3.7" (dcl-Control-GetProperty "AUTOSTITCH" "Palette" "Pitch" "Text"))
    (vl-every '(lambda (guide)
      (and (= -1 (ast:cad-get 'handedness (ast:cad-get 'settings (ast:cad-read guide))))
        (equal 3.0 (ast:cad-get 'pitch (ast:cad-get 'settings (ast:cad-read guide))) 1e-10))) (list first second)))
    "Changing face from a connected secondary guide updates every member while preserving the unsaved pitch draft"))

(defun ast:ui-tests (/ ast:*cad-test-passed* ast:*cad-test-failures* original-units original-tile settings guide output result state source-data output-data record generated-data generated-record landmarks partial-settings first second first-data second-data caption)
  (setq ast:*cad-test-passed* 0 ast:*cad-test-failures* nil
        original-units (getvar "INSUNITS") original-tile (getvar "TILEMODE")
        settings (ast:cad-default-settings))
  (setvar "INSUNITS" 4) (setvar "TILEMODE" 1)
  (c:AUTOSTITCH)
  (c:ASTUIINIT)
  (ast:cad-test-assert (and (not (ast:ui-test-enabled-p "Generate"))
                          (not (ast:ui-test-enabled-p "Add"))
                          (not (ast:ui-test-enabled-p "Delete"))
                          (equal "" (dcl-Control-GetProperty "AUTOSTITCH" "Palette" "Identity" "Caption")))
    "An empty palette disables actions that require a selected stitch line")
  (setq guide (entmakex '((0 . "LINE") (8 . "0") (10 0.0 1700.0 0.0) (11 30.0 1700.0 0.0))))
  (ast:ui-adopt (ast:cad-read guide))
  (ast:cad-test-assert (and (ast:cad-id-number (ast:cad-stitch-id guide))
    (equal (strcat "Stitch ID: " (ast:cad-stitch-id guide))
      (dcl-Control-GetProperty "AUTOSTITCH" "Palette" "Identity" "Caption"))
    (ast:marker-test-id guide (ast:marker-test-entities (ast:markers-reference guide))))
    "First selection shows the same new ST-number in the palette and boxed label")
  (setq result (ast:cad-generate guide settings nil) output (ast:cad-get 'output result))
  (ast:cad-require output "Could not create the palette generation fixture.")
  (ast:ui-adopt (ast:cad-read guide))
  (setq caption (dcl-Control-GetProperty "AUTOSTITCH" "Palette" "Seam" "Caption"))
  (ast:cad-test-assert (and (wcmatch caption "Guide length:*30*mm*")
                          (null (vl-string-search "|" caption))
                          (ast:ui-test-enabled-p "Start") (ast:ui-test-enabled-p "End")
                          (equal (strcat "Stitch ID: " (ast:cad-stitch-id guide))
                            (dcl-Control-GetProperty "AUTOSTITCH" "Palette" "Identity" "Caption")))
    "An open guide shows its ID and length with both endpoint controls enabled")
  (ast:cad-test-assert (and
    (equal "Add landmark" (dcl-Control-GetProperty "AUTOSTITCH" "Palette" "Add" "Caption"))
    (equal "Remove landmark" (dcl-Control-GetProperty "AUTOSTITCH" "Palette" "Delete" "Caption")))
    "Landmark actions name both the action and its object")
  (setq source-data (entget guide))
  (entmod (ast:cad-put 10 '(7.0 3.0 0.0) (ast:cad-put 41 2.0
    (ast:cad-put 50 0.3 (entget output)))))
  (setq output-data (entget output) record (ast:cad-record guide))
  (ast:ui-adopt (ast:cad-read guide))
  (ast:ui-put "Pitch" "Text" "not a number")
  (c:ASTUIGENERATE)
  (ast:cad-test-assert (and (equal output-data (entget output))
                          (equal record (ast:cad-record guide)))
    "Generate rejects invalid pitch without restoring or replacing moved output")
  (ast:ui-put "Pitch" "Text" "100")
  (c:ASTUIGENERATE)
  (ast:cad-test-assert (and (equal output-data (entget output))
                          (equal record (ast:cad-record guide)))
    "An infeasible Generate preserves transformed output and its saved pitch")
  (ast:ui-put "Pitch" "Text" "4")
  (c:ASTUIGENERATE)
  (setq state (ast:cad-read guide) generated-data (entget output) generated-record (ast:cad-record guide))
  (ast:cad-test-assert (and (equal source-data (entget guide))
    (equal 4.0 (ast:cad-get 'pitch (ast:cad-get 'settings state)) 1e-10)
    (ast:cad-placement-ok-p output) (not (ast:cad-get 'stale state)))
    "Generate applies the draft pitch and restores moved output to the unchanged guide")
  (vl-cmdf "_.UNDO" 1)
  (ast:cad-test-assert (and (equal output-data (entget output))
                          (equal record (ast:cad-record guide))
                          (equal source-data (entget guide)))
    "One Undo restores the transformed output and previous pitch together")
  (vl-cmdf "_.REDO")
  (ast:cad-test-assert (and (equal generated-data (entget output))
                          (equal generated-record (ast:cad-record guide)))
    "Redo restores the generated output and new pitch together")

  (setq guide (entmakex '((0 . "LINE") (8 . "0") (10 0.0 1750.0 0.0) (11 30.0 1750.0 0.0)))
        landmarks '(((primitive . 0) (station . 16.5)))
        partial-settings (append '((start . 3.0) (end . 27.0)) settings)
        partial-settings (ast:cad-put 'start-anchor
          (ast:cad-range-anchor guide '((primitive . 0) (station . 3.0))) partial-settings)
        partial-settings (ast:cad-put 'end-anchor
          (ast:cad-range-anchor guide '((primitive . 0) (station . 27.0))) partial-settings)
        result (ast:cad-generate guide partial-settings landmarks)
        source-data (entget guide) record (ast:cad-record guide))
  (ast:cad-require (ast:cad-get 'ok result) "Could not create the saved partial-guide fixture.")
  (ast:ui-adopt (ast:cad-read guide))
  (setq caption (dcl-Control-GetProperty "AUTOSTITCH" "Palette" "Seam" "Caption"))
  (ast:cad-test-assert (and (equal record (ast:cad-record guide))
    (wcmatch caption "Guide length:*24*mm*part*")
    (ast:ui-test-enabled-p "Start")
    (ast:ui-test-enabled-p "End")
    (equal "Set start" (dcl-Control-GetProperty "AUTOSTITCH" "Palette" "Start" "Caption")))
    "Selecting a partial guide preserves its inputs and exposes both endpoint controls")
  (c:ASTUIGENERATE)
  (setq state (ast:cad-read guide))
  (ast:cad-test-assert (and
    (equal 3.0 (ast:cad-get 'start (ast:cad-get 'settings state)) 1e-10)
    (equal 27.0 (ast:cad-get 'end (ast:cad-get 'settings state)) 1e-10)
    (not (ast:cad-get 'stale state)))
    "Generate retains saved partial coverage until its endpoints are changed")
  (ast:ui-put "Pitch" "Text" "3.4")
  (ast:ui-range-save 'start (trans '(6.0 1750.0 0.0) 0 1) (ast:ui-pitch))
  (setq state (ast:cad-read guide))
  (ast:cad-test-assert (and (equal source-data (entget guide))
    (equal 6.0 (ast:cad-get 'start (ast:cad-get 'settings state)) 1e-10)
    (equal 27.0 (ast:cad-get 'end (ast:cad-get 'settings state)) 1e-10)
    (equal 3.4 (ast:cad-get 'pitch (ast:cad-get 'settings state)) 1e-10)
    (equal landmarks (ast:cad-get 'landmarks state)))
    "Set start projects an interior point and preserves the pitch draft, end and landmarks")
  (c:ASTUIREVERSE)
  (ast:ui-range-save 'start (trans '(24.0 1750.0 0.0) 0 1) (ast:ui-pitch))
  (setq state (ast:cad-read guide))
  (ast:cad-test-assert (and (ast:cad-get 'reverse (ast:cad-get 'settings state))
    (equal 6.0 (ast:cad-get 'start (ast:cad-get 'settings state)) 1e-10)
    (equal 24.0 (ast:cad-get 'end (ast:cad-get 'settings state)) 1e-10))
    "After Reverse, Set start changes the displayed start at the guide's upper station")
  (setq record (ast:cad-record guide))
  (ast:ui-range-save 'end (trans '(26.0 1750.0 0.0) 0 1) (ast:ui-pitch))
  (ast:cad-test-assert (equal record (ast:cad-record guide))
    "A Set end pick crossing the displayed start leaves the saved seam unchanged")
  (ast:ui-range-save 'start "Default" (ast:ui-pitch))
  (setq state (ast:cad-read guide))
  (ast:cad-test-assert (and
    (null (assoc 'end (ast:cad-get 'settings state)))
    (null (assoc 'end-anchor (ast:cad-get 'settings state)))
    (equal 6.0 (ast:cad-get 'start (ast:cad-get 'settings state)) 1e-10))
    "Default restores only the selected displayed endpoint after reversal")
  (ast:ui-range-save 'start "WholeLine" (ast:ui-pitch))
  (setq state (ast:cad-read guide))
  (ast:cad-test-assert (and (equal source-data (entget guide))
    (equal landmarks (ast:cad-get 'landmarks state))
    (equal 3.4 (ast:cad-get 'pitch (ast:cad-get 'settings state)) 1e-10)
    (not (vl-some '(lambda (key) (assoc key (ast:cad-get 'settings state)))
      '(start end start-anchor end-anchor)))
    (ast:ui-test-enabled-p "Start") (ast:ui-test-enabled-p "End"))
    "WholeLine clears both saved limits while retaining guide, pitch and landmark")
  (c:ASTUILANDMARK 0 "Landmark 1")
  (c:ASTUIDELETE)
  (ast:cad-test-assert (and (null (ast:cad-get 'landmarks (ast:cad-read guide)))
                          (not (ast:ui-test-enabled-p "Delete"))
                          (equal source-data (entget guide)))
    "Remove landmark deletes its constraint and disables itself when no landmarks remain")
  (setq partial-settings (ast:cad-put 'end-anchor
          (ast:cad-range-anchor guide '((primitive . 0) (station . 30.0)))
          (ast:cad-put 'end 30.0 settings)))
  (ast:cad-save-inputs guide partial-settings nil)
  (ast:ui-adopt (ast:cad-read guide))
  (ast:ui-range-save 'end "Default" (ast:ui-pitch))
  (ast:cad-test-assert (and (ast:ui-test-enabled-p "Start") (ast:ui-test-enabled-p "End")
    (null (assoc 'end-anchor (ast:cad-get 'settings (ast:cad-read guide)))))
    "Default removes a saved endpoint anchor even when it currently reaches the full guide")

  (setq guide (entmakex '((0 . "CIRCLE") (8 . "0") (10 100.0 1750.0 0.0) (40 . 10.0))))
  (ast:ui-adopt (ast:cad-read guide))
  (ast:cad-test-assert (and (ast:ui-test-enabled-p "Start")
    (not (ast:ui-test-enabled-p "End"))
    (equal "Set start" (dcl-Control-GetProperty "AUTOSTITCH" "Palette" "Start" "Caption")))
    "A closed guide enables Set start and disables Set end")
  (ast:ui-range-save 'start (trans '(100.0 1760.0 0.0) 0 1) (ast:ui-pitch))
  (ast:cad-test-assert (equal (* 5.0 pi)
    (ast:cad-get 'phase (ast:cad-get 'settings (ast:cad-read guide))) 1e-8)
    "Set start on a closed guide saves the chosen loop phase")
  (ast:cad-save-inputs guide
    (append '((start . 1.0) (end . 2.0)) (ast:cad-get 'settings (ast:cad-read guide))) nil)
  (ast:ui-adopt (ast:cad-read guide))
  (ast:ui-range-save 'start "Default" (ast:ui-pitch))
  (setq state (ast:cad-read guide))
  (ast:cad-test-assert (and (equal 0.0 (ast:cad-get 'phase (ast:cad-get 'settings state)) 1e-8)
    (not (vl-some '(lambda (key) (assoc key (ast:cad-get 'settings state)))
      '(start end start-anchor end-anchor)))
    (null (ast:cad-get 'range-conflict state)))
    "Set start on a loop removes obsolete endpoint limits left by a former open guide")

  (setq first (entmakex '((0 . "LINE") (8 . "0") (10 -10.5 1800.0 0.0) (11 10.5 1800.0 0.0)))
        second (entmakex '((0 . "LINE") (8 . "0") (10 0.0 1800.0 0.0) (11 0.0 1810.5 0.0)))
        result (ast:cad-connect first second '(0.0 1800.0 0.0) settings nil)
        output (ast:cad-get 'output result) first-data (entget first) second-data (entget second))
  (ast:cad-require output "Could not create the connected palette fixture.")
  (entmod (ast:cad-put 10 '(9.0 4.0 0.0) (ast:cad-put 41 0.5
    (ast:cad-put 42 0.5 (entget output)))))
  (ast:ui-adopt (ast:cad-read second))
  (c:ASTUIGENERATE)
  (ast:cad-test-assert (and (ast:cad-placement-ok-p output)
    (equal first-data (entget first)) (equal second-data (entget second))
    (equal output (ast:cad-get 'output (ast:cad-read first)))
    (equal output (ast:cad-get 'output (ast:cad-read second)))
    (not (ast:cad-get 'stale (ast:cad-read first)))
    (not (ast:cad-get 'stale (ast:cad-read second)))
    (equal (ast:cad-stitch-id first) (ast:cad-stitch-id second))
    (equal (strcat "Stitch ID: " (ast:cad-stitch-id first))
      (dcl-Control-GetProperty "AUTOSTITCH" "Palette" "Identity" "Caption")))
    "Generate from a connected member restores the shared output and displays its shared ID")
  (setq caption (ast:cad-stitch-id first))
  (foreach guide (list first second output)
    (setq record (ast:cad-record guide))
    (ast:cad-write-record guide
      (vl-remove-if '(lambda (item) (member (car item) '(stitch-id stitch-owner output-identity link))) record)
      (ast:cad-get 'link record)))
  (ast:ui-adopt (ast:cad-read second))
  (ast:cad-test-assert (and (ast:cad-id-number (ast:cad-stitch-id first))
    (/= caption (ast:cad-stitch-id first)) (= caption (cdr (assoc 2 (entget output))))
    (equal (strcat "Stitch ID: " (ast:cad-stitch-id first))
      (dcl-Control-GetProperty "AUTOSTITCH" "Palette" "Identity" "Caption"))
    (ast:marker-test-id first (ast:marker-test-entities (ast:markers-reference first))))
    "Selecting a legacy connected secondary member refreshes the primary boxed ID without regenerating output")
  (ast:ui-test-matching-registration)
  (ast:ui-test-matching)
  (setvar "INSUNITS" original-units) (setvar "TILEMODE" original-tile)
  (list (cons 'passed ast:*cad-test-passed*) (cons 'failed (length ast:*cad-test-failures*))
        (cons 'failures (reverse ast:*cad-test-failures*))))
(princ)
