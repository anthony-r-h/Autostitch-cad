;;; Native database/display tests. Use a dedicated disposable model-space drawing.
;;; Load geometry, CAD, markers and autostitch-cad-tests.lsp before calling ast:marker-tests.

(defun ast:marker-test-entities (reference / entity data result)
  (if (and reference (entget reference))
    (progn
      (setq entity (tblobjname "BLOCK" (cdr (assoc 2 (entget reference)))))
      (while (and (setq entity (entnext entity))
                  (/= (cdr (assoc 0 (setq data (entget entity)))) "ENDBLK"))
        (setq result (cons data result)))))
  (reverse result))

(defun ast:marker-test-type (kind entities)
  (vl-remove-if-not '(lambda (data) (= kind (cdr (assoc 0 data)))) entities))

(defun ast:marker-test-bars (entities)
  (vl-remove-if-not '(lambda (data) (= 2 (cdr (assoc 90 data))))
    (ast:marker-test-type "LWPOLYLINE" entities)))

(defun ast:marker-test-id (guide entities)
  (car (vl-remove-if-not '(lambda (data) (= (ast:cad-stitch-id guide) (cdr (assoc 1 data))))
    (ast:marker-test-type "TEXT" entities))))

(defun ast:marker-test-boxes (entities)
  (vl-remove-if-not '(lambda (data) (and (= 4 (cdr (assoc 90 data))) (= 1 (cdr (assoc 70 data)))))
    (ast:marker-test-type "LWPOLYLINE" entities)))

(defun ast:marker-test-id-opposite (guide entities / start text point)
  (setq start (car (vl-remove-if-not '(lambda (data) (= "S" (cdr (assoc 1 data))))
    (ast:marker-test-type "TEXT" entities))) text (ast:marker-test-id guide entities)
    point (ast:marker-test-label-centre "S" entities))
  (ast:cad-test-assert (and start text point
    (equal (mapcar '+ (cdr (assoc 11 start)) (cdr (assoc 11 text)))
      (mapcar '(lambda (coordinate) (* 2.0 coordinate)) point) 1e-8))
    "Stitch ID is centred opposite the displayed S across the guide"))

(defun ast:marker-test-centres (entities)
  (mapcar '(lambda (data) (cdr (assoc 10 data))) (ast:marker-test-type "POINT" entities)))

(defun ast:marker-test-label-centre (label entities / text nearest point data)
  (foreach data (ast:marker-test-type "TEXT" entities)
    (if (equal label (cdr (assoc 1 data))) (setq text (cdr (assoc 11 data)))))
  (if text
    (foreach point (ast:marker-test-centres entities)
      (if (or (null nearest) (< (distance text point) (distance text nearest)))
        (setq nearest point))))
  nearest)

(defun ast:marker-test-block-count (/ count record)
  (setq count 0 record (tblnext "BLOCK" T))
  (while record (setq count (1+ count) record (tblnext "BLOCK")))
  count)

(defun ast:marker-test-snap-at (point pick mode / actual)
  (setq actual (osnap (trans pick 0 1) mode))
  (if actual (setq actual (trans actual 1 0)))
  (ast:cad-test-assert (equal point actual 1e-8)
    (strcat mode " snaps exactly to requested marker centre; pick=" (vl-prin1-to-string pick)
      "; actual=" (vl-prin1-to-string actual))))

(defun ast:marker-test-snap (point mode)
  (ast:marker-test-snap-at point (mapcar '+ point '(0.025 0.025 0.0)) mode))

(defun ast:marker-test-compare (label checks / check failures)
  (foreach check checks
    (if (not (equal (cadr check) (caddr check)))
      (setq failures (cons check failures))))
  (ast:cad-test-assert (null failures)
    (strcat label (if failures (strcat " | differences=" (vl-prin1-to-string (reverse failures))) ""))))

(defun ast:marker-test-erase-sync (guide)
  (ast:cad-require (entdel guide) "Marker test could not erase its source fixture.")
  (ast:markers-sync)
  (list '(ok . T)))

(defun ast:marker-test-shared-node (/ settings first second result first-entities second-entities entities circles points)
  (setq settings (ast:cad-default-settings))
  (entmake '((0 . "LINE") (8 . "0") (10 1100.0 1000.0 0.0) (11 1127.0 1000.0 0.0)))
  (setq first (entlast) result (ast:cad-generate first settings nil))
  (ast:cad-require (ast:cad-get 'ok result) "Could not generate shared-marker first source.")
  (entmake '((0 . "LINE") (8 . "0") (10 1113.5 1000.0 0.0) (11 1113.5 1013.5 0.0)))
  (setq second (entlast) result (ast:cad-generate second settings nil))
  (ast:cad-require (ast:cad-get 'ok result) "Could not generate shared-marker second source.")
  (setq result (ast:cad-connect first second nil settings nil))
  (ast:cad-test-assert (ast:cad-get 'ok result)
    (strcat "Shared-marker T fixture connects; result=" (vl-prin1-to-string result)))
  (if (ast:cad-get 'ok result)
    (progn
      (setq first-entities (ast:marker-test-entities (ast:markers-reference first))
            second-entities (ast:marker-test-entities (ast:markers-reference second))
            entities (append first-entities second-entities)
            circles (vl-remove-if-not '(lambda (data)
              (equal '(1113.5 1000.0 0.0) (cdr (assoc 10 data)) 1e-8))
              (ast:marker-test-type "CIRCLE" entities))
            points (vl-remove-if-not '(lambda (data)
              (equal '(1113.5 1000.0 0.0) (cdr (assoc 10 data)) 1e-8))
              (ast:marker-test-type "POINT" entities)))
      (ast:cad-test-assert (and (= 1 (length (ast:marker-test-boxes entities)))
        (ast:marker-test-id first first-entities) (null (ast:marker-test-id second second-entities))
        (equal (ast:cad-stitch-id first) (ast:cad-stitch-id second)))
        "Connected guides share one stable ID and display its box on the owning guide only")
      (ast:cad-test-assert (and (= 1 (length circles)) (= 1 (length points)))
        "A shared T node has exactly one editing circle and point across both member helpers")
      (ast:cad-test-assert (and
        (equal '(1113.5 1000.0 0.0) (ast:marker-test-label-centre "J" first-entities) 1e-8)
        (null (ast:marker-test-label-centre "S" second-entities))
        (equal '(1113.5 1013.5 0.0) (ast:marker-test-label-centre "E" second-entities) 1e-8))
        "Shared J label replaces overlapping secondary S while its free E remains")
      (ast:cad-test-assert (equal (ast:markers-connections first) (ast:markers-connections second))
        "Every connected member resolves the same live shared-node positions")
      (vla-ZoomCenter (vlax-get-acad-object) (vlax-3d-point '(1113.5 1006.0 0.0)) 60.0)
      (vla-Regen (vla-get-ActiveDocument (vlax-get-acad-object)) 1)
      (ast:marker-test-snap '(1113.5 1000.0 0.0) "_cen,_nod"))))

(defun ast:marker-test-compact-geometry (/ guide state result entities bars vertices midpoint normal tangent labels settings arrow station point)
  (entmake (list '(0 . "ARC") '(8 . "0") '(10 1200.0 1000.0 0.0) '(40 . 10.0)
    '(50 . 0.0) (cons 51 (/ pi 2.0))))
  (setq guide (entlast) state (ast:cad-read guide)
        result (ast:markers-ensure guide (ast:cad-get 'settings state)
          (list (list '(primitive . 0) (cons 'station (* 2.5 pi))))
          (ast:cad-get 'factor state) (ast:cad-get 'route state))
        entities (ast:marker-test-entities (ast:markers-reference guide))
        bars (ast:marker-test-bars entities)
        vertices (mapcar 'cdr (vl-remove-if-not '(lambda (item) (= 10 (car item))) (car bars)))
        midpoint (mapcar '(lambda (aa bb) (/ (+ aa bb) 2.0)) (car vertices) (cadr vertices))
        normal (mapcar '- (car vertices) (cadr vertices)) tangent (list (- (sqrt 0.5)) (sqrt 0.5)))
  (ast:cad-test-assert (and (ast:cad-get 'ok result) (= 1 (length bars))
    (equal midpoint (list (+ 1200.0 (sqrt 50.0)) (+ 1000.0 (sqrt 50.0))) 1e-8)
    (equal 0.0 (apply '+ (mapcar '* normal tangent)) 1e-8)
    (equal 2.4 (distance (car vertices) (cadr vertices)) 1e-8))
    "Curved landmark bar crosses the exact selected point normal to the local tangent")
  (ast:marker-test-id-opposite guide entities)
  (ast:cad-test-assert (and (equal '(1210.8 1000.0 0.0)
    (cdr (assoc 11 (ast:marker-test-id guide entities))) 1e-8)
    (equal (/ pi 2.0) (cdr (assoc 50 (ast:marker-test-id guide entities))) 1e-8))
    "Curved start ID follows the local tangent and stays clear of the guide")
  (entmake '((0 . "LWPOLYLINE") (100 . "AcDbEntity") (8 . "0") (100 . "AcDbPolyline")
    (90 . 3) (70 . 0) (10 1250.0 1000.0) (10 1260.0 1000.0) (10 1260.0 1010.0)))
  (setq guide (entlast) state (ast:cad-read guide)
        result (ast:markers-ensure guide (ast:cad-get 'settings state) nil
          (ast:cad-get 'factor state) (ast:cad-get 'route state))
        entities (ast:marker-test-entities (ast:markers-reference guide))
        labels (mapcar '(lambda (data) (cdr (assoc 1 data))) (ast:marker-test-type "TEXT" entities)))
  (ast:cad-test-assert (and (ast:cad-get 'ok result) (member "J" labels)
    (equal '(1260.0 1000.0 0.0) (ast:marker-test-label-centre "J" entities) 1e-8)
    (not (member "CORNER" labels))) "A corner within one polyline uses the same compact J notation")
  (entmake '((0 . "CIRCLE") (8 . "0") (10 1300.0 1000.0 0.0) (40 . 10.0)))
  (setq guide (entlast) state (ast:cad-read guide)
        settings (ast:cad-put 'reverse T (ast:cad-put 'phase 0.5 (ast:cad-get 'settings state)))
        result (ast:markers-ensure guide settings nil (ast:cad-get 'factor state) (ast:cad-get 'route state))
        entities (ast:marker-test-entities (ast:markers-reference guide))
        arrow (car (vl-remove-if-not '(lambda (data) (= ">" (cdr (assoc 1 data))))
          (ast:marker-test-type "TEXT" entities)))
        station (- (* 20.0 pi) 1.0) point (vlax-curve-getPointAtDist guide station))
  (ast:cad-test-assert (and (ast:cad-get 'ok result) arrow
    (equal point (cdr (assoc 11 arrow)) 1e-8)
    (equal -1.0 (cos (- (cdr (assoc 50 arrow))
      (angle '(0.0 0.0 0.0) (vlax-curve-getFirstDeriv guide (vlax-curve-getParamAtPoint guide point))))) 1e-8))
    "Closed reversed direction cue wraps behind the start phase on the guide")
  (ast:marker-test-id-opposite guide entities)
  (setvar "INSUNITS" 1)
  (entmake '((0 . "LINE") (8 . "0") (10 50.0 50.0 0.0) (11 52.0 50.0 0.0)))
  (setq guide (entlast) state (ast:cad-read guide)
        result (ast:markers-ensure guide (ast:cad-get 'settings state) '(((primitive . 0) (station . 15.0)))
          (ast:cad-get 'factor state) (ast:cad-get 'route state))
        entities (ast:marker-test-entities (ast:markers-reference guide)) bars (ast:marker-test-bars entities)
        vertices (mapcar 'cdr (vl-remove-if-not '(lambda (item) (= 10 (car item))) (car bars))))
  (ast:cad-test-assert (and (ast:cad-get 'ok result) (= 1 (length bars))
    (equal (/ 0.12 25.4) (cdr (assoc 43 (car bars))) 1e-8)
    (equal (/ 2.4 25.4) (distance (car vertices) (cadr vertices)) 1e-8)
    (not (vl-some '(lambda (data) (not (equal (/ (if (= (ast:cad-stitch-id guide) (cdr (assoc 1 data))) 0.528 0.66) 25.4) (cdr (assoc 40 data)) 1e-8)))
      (ast:marker-test-type "TEXT" entities)))) "Inch drawings preserve physical label and landmark-bar sizes")
  (ast:marker-test-id-opposite guide entities)
  (ast:cad-test-assert (equal (/ 0.8 25.4)
    (distance '(50.0 50.0 0.0) (cdr (assoc 11 (ast:marker-test-id guide entities)))) 1e-8)
    "ID offset scales to drawing units")
  (setvar "INSUNITS" 4))

(defun ast:marker-test-junction-id (/ first second result settings entities text boxes vertices)
  (setq settings (ast:cad-default-settings))
  (entmake '((0 . "LINE") (8 . "0") (10 1400.0 1000.0 0.0) (11 1400.0 1013.5 0.0)))
  (setq first (entlast))
  (entmake '((0 . "LINE") (8 . "0") (10 1386.5 1000.0 0.0) (11 1413.5 1000.0 0.0)))
  (setq second (entlast) result (ast:cad-connect first second nil settings nil))
  (ast:cad-test-assert (ast:cad-get 'ok result) "Shared-start ID fixture connects")
  (if (ast:cad-get 'ok result)
    (progn
      (setq entities (ast:marker-test-entities (ast:markers-reference first))
            text (ast:marker-test-id first entities) boxes (ast:marker-test-boxes entities)
            vertices (mapcar 'cdr (vl-remove-if-not '(lambda (item) (= 10 (car item))) (car boxes))))
      (ast:cad-test-assert (and text (null (ast:marker-test-label-centre "S" entities))
        (equal '(1400.0 1000.0 0.0) (ast:marker-test-label-centre "J" entities) 1e-8)
        (equal '(1400.8 1001.5 0.0) (cdr (assoc 11 text)) 1e-8)
        (not (vl-some '(lambda (point) (<= (car point) 1400.0)) vertices)))
        "At a shared start the boxed ID moves half a pitch along the path, clear of J and the guide"))))

(defun ast:marker-test-body (/ document guide settings landmarks result output reference entities centres labels
    state blocks record marker-record marker-data output-data first-name old-name old-settings style heights
    changed-settings copied-reference data stage bars vertices texts old-style legacy-record)
  (setq document (vla-get-ActiveDocument (vlax-get-acad-object))
        settings (ast:cad-default-settings) landmarks '(((primitive . 0) (station . 16.5))))
  (entmake '((0 . "LINE") (8 . "0") (10 1000.0 1000.0 0.0) (11 1030.0 1000.0 0.0)))
  (setq guide (entlast))
  (vla-ZoomCenter (vlax-get-acad-object) (vlax-3d-point '(1015.0 1000.0 0.0)) 60.0)
  (setq result (ast:cad-generate guide settings landmarks))
  (ast:cad-test-assert (ast:cad-get 'ok result)
    (strcat "Marker fixture generates; result=" (vl-prin1-to-string result)))
  (if (ast:cad-get 'ok result)
    (progn
      (setq output (ast:cad-get 'output result) reference (ast:markers-reference guide)
            entities (ast:marker-test-entities reference) centres (ast:marker-test-centres entities)
            labels (mapcar '(lambda (data) (cdr (assoc 1 data))) (ast:marker-test-type "TEXT" entities)))
      (ast:cad-test-assert (and reference (= (length centres) 3) (= 2 (length (ast:marker-test-type "CIRCLE" entities)))
        (vl-some '(lambda (point) (equal point '(1000.0 1000.0 0.0) 1e-8)) centres)
        (vl-some '(lambda (point) (equal point '(1030.0 1000.0 0.0) 1e-8)) centres)
        (vl-some '(lambda (point) (equal point '(1016.5 1000.0 0.0) 1e-8)) centres))
        "Three exact snap points mark both endpoints and the landmark; only endpoints retain circles")
      (ast:cad-test-assert (and (= (length labels) 5) (member "S" labels)
        (member "E" labels) (member "L1" labels) (member ">" labels))
        "Compact S/E/L1 labels retain their meanings and direction cue")
      (ast:marker-test-id-opposite guide entities)
      (setq texts (list (ast:marker-test-id guide entities)) bars (ast:marker-test-boxes entities))
      (ast:cad-test-assert (and (= 1 (length bars)) (car texts)
        (= 7 (cdr (assoc 62 (car bars)))) (= 9 (cdr (assoc 370 (car bars))))
        (= 7 (cdr (assoc 62 (car texts)))) (= 9 (cdr (assoc 370 (car texts))))
        (equal 0.528 (cdr (assoc 40 (car texts))) 1e-8)
        (equal (ast:cad-stitch-id guide)
          (ast:cad-get 'stitch-id (ast:cad-get 'snapshot (ast:markers-record guide))))
        (eq T (ast:cad-get 'id-owner (ast:cad-get 'snapshot (ast:markers-record guide)))))
        "One subtle monochrome ID box has small text, thin strokes and saved stable identity")
      (setq texts (vl-remove-if-not '(lambda (data) (= ">" (cdr (assoc 1 data))))
        (ast:marker-test-type "TEXT" entities)))
      (ast:cad-test-assert (and (= 1 (length texts))
        (equal '(1001.5 1000.0 0.0) (cdr (assoc 11 (car texts))) 1e-8)
        (equal 0.0 (cdr (assoc 50 (car texts))) 1e-8))
        "Direction cue sits on the guide half a pitch after S")
      (ast:cad-test-assert (and (equal '(1000.0 1000.0 0.0) (ast:marker-test-label-centre "S" entities) 1e-8)
        (equal '(1030.0 1000.0 0.0) (ast:marker-test-label-centre "E" entities) 1e-8))
        "S and E labels identify the correct source endpoints")
      (setq texts (vl-remove-if-not '(lambda (data) (member (cdr (assoc 1 data)) '("S" "E")))
        (ast:marker-test-type "TEXT" entities)))
      (ast:cad-test-assert (and (= 2 (length texts))
        (not (vl-some '(lambda (data) (not (equal 0.8 (distance (cdr (assoc 11 data))
          (ast:marker-test-label-centre (cdr (assoc 1 data)) entities)) 1e-8))) texts)))
        "Endpoint label centres sit 0.8 mm from the stitch line")
      (ast:cad-test-assert (and (= 0 (cdr (assoc 290 (entget (tblobjname "LAYER" "AUTOSTITCH_UI")))))
        (= "AUTOSTITCH_UI" (cdr (assoc 8 (entget reference))))
        (not (vl-some '(lambda (data) (/= "AUTOSTITCH_UI" (cdr (assoc 8 data)))) entities)))
        "Helper reference and all nested graphics remain on the nonplotting editing layer")
      (ast:cad-test-assert (= "AUTOSTITCH" (cdr (assoc 8 (entget output))))
        "Physical openings retain their separate output layer")
      (ast:cad-test-assert (equal guide (ast:markers-guide reference)) "Selecting an editing helper resolves its owning path")

      (vla-Regen document 1)
      (ast:marker-test-snap '(1016.5 1000.0 0.0) "_nod")
      (ast:marker-test-snap '(1016.5 1000.0 0.0) "_mid")
      (ast:marker-test-snap '(1000.0 1000.0 0.0) "_cen,_nod")
      (ast:marker-test-snap '(1030.0 1000.0 0.0) "_cen,_nod")
      (setq bars (ast:marker-test-bars entities)
            vertices (mapcar 'cdr (vl-remove-if-not '(lambda (item) (= 10 (car item))) (car bars))))
      (ast:cad-test-assert (and (= 1 (length bars)) (= 2 (length vertices))
        (equal 0.12 (cdr (assoc 43 (car bars))) 1e-8)
        (equal '((1016.5 1001.2) (1016.5 998.8)) vertices 1e-8))
        "Landmark is one heavy 2.4 mm transverse bar centred at the selected reference")
      (ast:cad-test-assert (equal entities (ast:marker-test-entities reference))
        "Regen preserves all saved marker geometry")

      (setq marker-record (ast:markers-record guide) old-style '((size . 1.0) (text-height . 1.2))
            legacy-record (ast:cad-put 'style old-style (ast:cad-put 'snapshot
              (ast:cad-put 'display-version 8 (ast:cad-get 'snapshot marker-record)) marker-record)))
      (ast:markers-write-record guide (vl-remove-if '(lambda (item) (= 'link (car item))) legacy-record) reference)
      (setq state (ast:cad-read guide) result (ast:markers-ensure guide (ast:cad-get 'settings state)
        (ast:cad-get 'landmarks state) (ast:cad-get 'factor state) (ast:cad-get 'route state)))
      (ast:cad-test-assert (and (ast:cad-get 'ok result)
        (equal 11 (ast:cad-get 'display-version (ast:cad-get 'snapshot (ast:markers-record guide))))
        (equal 0.66 (ast:cad-get 'text-height (ast:cad-get 'style (ast:markers-record guide))) 1e-8))
        "Existing large marker styles migrate to compact labels on inspection")

      (setq blocks (ast:marker-test-block-count) record (ast:cad-record guide)
            marker-record (ast:markers-record guide) marker-data (entget reference)
            state (ast:cad-read guide))
      (repeat 3
        (ast:markers-ensure guide (ast:cad-get 'settings state) (ast:cad-get 'landmarks state)
          (ast:cad-get 'factor state) (ast:cad-get 'route state)))
      (ast:cad-test-assert (and (= blocks (ast:marker-test-block-count))
        (equal record (ast:cad-record guide)) (equal marker-record (ast:markers-record guide))
        (equal marker-data (entget reference))) "Repeated existing-path inspection adds no block or source revision")

      (setq data (entget guide))
      (entmod (ast:cad-put 10 '(1000.0 1010.0 0.0) (ast:cad-put 11 '(1030.0 1010.0 0.0) data)))
      (setq state (ast:cad-read guide)
            result (ast:markers-ensure guide (ast:cad-get 'settings state) (ast:cad-get 'landmarks state)
              (ast:cad-get 'factor state) (ast:cad-get 'route state)))
      (ast:cad-test-assert (and (ast:cad-get 'ok result)
        (equal '(1000.0 1010.0 0.0) (ast:marker-test-label-centre "S" (ast:marker-test-entities reference)) 1e-8)
        (equal '(1016.5 1010.0 0.0) (ast:marker-test-label-centre "L1" (ast:marker-test-entities reference)) 1e-8))
        "Explicit inspection refreshes stale endpoints and landmark snaps after a source move")
      (entmod data)
      (setq state (ast:cad-read guide))
      (ast:markers-ensure guide (ast:cad-get 'settings state) (ast:cad-get 'landmarks state)
        (ast:cad-get 'factor state) (ast:cad-get 'route state))

      (setq first-name (cdr (assoc 2 (entget reference))) settings (ast:cad-put 'pitch 3.25 settings)
            result (ast:cad-save-inputs guide settings landmarks))
      (ast:cad-test-assert (and (ast:cad-get 'ok result) (equal reference (ast:markers-reference guide))
        (/= first-name (cdr (assoc 2 (entget reference))))) "Saving pitch refreshes the existing marker reference in its transaction")
      (setq old-name (cdr (assoc 2 (entget reference))) old-settings settings
            settings (ast:cad-put 'reverse T (ast:cad-put 'start 3.0 (ast:cad-put 'end 27.0 settings)))
            result (ast:cad-save-inputs guide settings landmarks)
            entities (ast:marker-test-entities reference) first-name (cdr (assoc 2 (entget reference))))
      (ast:cad-test-assert (and (ast:cad-get 'ok result)
        (equal '(1027.0 1000.0 0.0) (ast:marker-test-label-centre "S" entities) 1e-8)
        (equal '(1003.0 1000.0 0.0) (ast:marker-test-label-centre "E" entities) 1e-8))
        "Trimmed reversed path labels follow actual traversal start and end")
      (ast:marker-test-id-opposite guide entities)
      (ast:cad-test-assert (equal '(1027.0 999.2 0.0)
        (cdr (assoc 11 (ast:marker-test-id guide entities))) 1e-8)
        "Reversed trimmed guide moves its ID to the displayed traversal start")
      (setq texts (vl-remove-if-not '(lambda (item) (= ">" (cdr (assoc 1 item))))
        (ast:marker-test-type "TEXT" entities)))
      (ast:cad-test-assert (and (= 1 (length texts))
        (equal '(1025.375 1000.0 0.0) (cdr (assoc 11 (car texts))) 1e-8)
        (equal pi (cdr (assoc 50 (car texts))) 1e-8))
        "Reversed trimmed direction cue starts near its displayed S and points backward")
      (vl-cmdf "_.UNDO" "1")
      (ast:marker-test-compare "One Undo restores source inputs and marker definition together"
        (list (list 'marker-definition old-name (cdr (assoc 2 (entget reference))))
          (list 'source-settings old-settings (ast:cad-get 'settings (ast:cad-read guide)))))
      (vl-cmdf "_.REDO")
      (ast:cad-test-assert (and (equal first-name (cdr (assoc 2 (entget reference))))
        (equal settings (ast:cad-get 'settings (ast:cad-read guide))))
        "One Redo restores source inputs and marker definition together")

      (setq style (ast:cad-get 'style (ast:markers-record guide))
            heights (mapcar '(lambda (data) (cdr (assoc 40 data)))
              (ast:marker-test-type "TEXT" (ast:marker-test-entities reference))))
      (ast:cad-test-assert (and heights (not (vl-some '(lambda (height) (not (or (equal height 0.66 1e-8) (equal height 0.528 1e-8)))) heights)))
        "Labels retain 0.66 mm text with a smaller 0.528 mm stitch ID")
      (vla-ZoomCenter (vlax-get-acad-object) (vlax-3d-point '(1015.0 1000.0 0.0)) 600.0)
      (setq settings (ast:cad-put 'pitch 3.5 settings) result (ast:cad-save-inputs guide settings landmarks))
      (ast:cad-test-assert (and (ast:cad-get 'ok result) (equal style (ast:cad-get 'style (ast:markers-record guide)))
        (equal heights (mapcar '(lambda (data) (cdr (assoc 40 data)))
          (ast:marker-test-type "TEXT" (ast:marker-test-entities reference)))))
        "Zoom and an actual input save preserve initial label size")

      (setq settings (ast:cad-default-settings) result (ast:cad-generate guide settings landmarks))
      (ast:cad-test-assert (ast:cad-get 'ok result) "Restore full-range fixture before rollback injection")
      (if (ast:cad-get 'ok result)
        (progn
          (setq record (ast:cad-record guide) marker-record (ast:markers-record guide)
                marker-data (entget reference) output-data (entget output)
                entities (ast:marker-test-entities reference)
                changed-settings (ast:cad-put 'reverse T settings))
          (foreach stage '("output-metadata" "marker-metadata")
            (setq ast:*cad-fail-stage* stage result (ast:cad-generate guide changed-settings landmarks)
                  ast:*cad-fail-stage* nil)
            (ast:cad-test-assert (and (not (ast:cad-get 'ok result))
              (equal (strcat "Injected failure: " stage) (ast:cad-get 'error result)))
              (strcat "Failure reaches the intended transaction stage: " stage))
            (ast:marker-test-compare
              (strcat "Failure restores source, cuts, marker reference and visible points: " stage)
              (list (list 'source-record record (ast:cad-record guide))
                (list 'marker-record marker-record (ast:markers-record guide))
                (list 'marker-reference marker-data (entget reference))
                (list 'output-reference output-data (entget output))
                (list 'visible-marker-geometry entities (ast:marker-test-entities reference)))))))

      (setq copied-reference (vlax-vla-object->ename (vla-Copy (vlax-ename->vla-object reference))))
      (ast:cad-test-assert (and (null (ast:markers-guide copied-reference))
        (equal guide (ast:markers-guide reference))) "A helper-only copy cannot claim the original source")
      (setq result (ast:cad-transaction 'ast:marker-test-erase-sync (list guide)))
      (ast:cad-test-assert (and (ast:cad-get 'ok result) (null (entget guide))
        (null (entget reference)) (null (entget copied-reference)))
        "Manual reconciliation removes erased-source and nonreciprocal copied helpers")
      (vl-cmdf "_.UNDO" "1")
      (ast:marker-test-compare "Undo of grouped cleanup restores the source and its marker association"
        (list (list 'source-exists T (if (entget guide) T nil))
          (list 'marker-exists T (if (entget reference) T nil))
          (list 'marker-owner guide (ast:markers-guide reference)))))))

(defun ast:marker-tests (/ ast:*cad-test-passed* ast:*cad-test-failures* original-units original-echo
    original-aperture original-view-height original-view-centre original-fail-stage result)
  (setq ast:*cad-test-passed* 0 ast:*cad-test-failures* nil
        original-units (getvar "INSUNITS") original-echo (getvar "CMDECHO")
        original-aperture (getvar "APERTURE") original-view-height (getvar "VIEWSIZE")
        original-view-centre (getvar "VIEWCTR")
        original-fail-stage ast:*cad-fail-stage*)
  (if (= 2 (length original-view-centre)) (setq original-view-centre (append original-view-centre '(0.0))))
  (setq original-view-centre (trans original-view-centre 1 0))
  (setvar "INSUNITS" 4) (setvar "CMDECHO" 0) (setvar "APERTURE" 20)
  (setq ast:*cad-fail-stage* nil)
  (setq result (vl-catch-all-apply '(lambda () (ast:marker-test-body) (ast:marker-test-shared-node)
    (ast:marker-test-compact-geometry) (ast:marker-test-junction-id)) nil))
  (setq ast:*cad-fail-stage* original-fail-stage)
  (setvar "INSUNITS" original-units) (setvar "CMDECHO" original-echo) (setvar "APERTURE" original-aperture)
  (vla-ZoomCenter (vlax-get-acad-object) (vlax-3d-point original-view-centre) original-view-height)
  (if (vl-catch-all-error-p result)
    (ast:cad-test-assert nil (strcat "Marker suite runtime error: " (vl-catch-all-error-message result))))
  (list (cons 'passed ast:*cad-test-passed*) (cons 'failed (length ast:*cad-test-failures*))
    (cons 'failures (reverse ast:*cad-test-failures*))))

(princ)
