;;; Pure matching-copy tests. Load geometry, network and match-geometry first.
(defun ast:m-test (condition label)
  (setq ast:m-test-count (1+ ast:m-test-count))
  (if (not condition) (setq ast:m-test-failures (cons label ast:m-test-failures))))
(defun ast:m-test-line (aa bb) (list '(kind . line) (cons 'a aa) (cons 'b bb)))
(defun ast:m-test-arc (center radius start sweep)
  (list '(kind . arc) (cons 'center center) (cons 'radius radius) (cons 'start-angle start) (cons 'sweep sweep)))
(defun ast:m-test-route (primitives closed) (list (cons 'primitives primitives) (cons 'closed closed)))
(defun ast:m-test-map (source target parity reversed)
  (ast:m-map-routes (list source) (list target) parity reversed nil nil))
(defun ast:m-test-expected (point parity)
  ;; Independent fixtures: quarter-turn plus translation, optionally reflected.
  (list (- 20.0 (* parity (cadr point))) (+ 30.0 (car point))))
(defun ast:m-tests (/ ast:m-test-count ast:m-test-failures line target reversed result transform source arc split circle target-circle square target-square paths targets branch lower pair changed settings solution copy parity source-opening target-opening index interval connection incidence expected original inverse)
  (setq ast:m-test-count 0 ast:m-test-failures nil
        line (ast:m-test-route (list (ast:m-test-line '(0.0 0.0) '(30.0 0.0))) nil)
        target (ast:m-test-route (list (ast:m-test-line '(20.0 30.0) '(20.0 60.0))) nil))
  (foreach parity '(1 -1)
    (setq result (ast:m-test-map line target parity nil) transform (ast:g-get 'transform result nil))
    (ast:m-test (ast:g-get 'ok result nil) (strcat "straight explicit face " (itoa parity)))
    (ast:m-test (equal (ast:m-point '(4.0 2.0) transform) (ast:m-test-expected '(4.0 2.0) parity) 1e-8)
      (strcat "straight off-guide point preserves chosen face " (itoa parity)))
    (ast:m-test (equal (ast:m-vector '(0.6 0.8) transform) (list (* (- parity) 0.8) 0.6) 1e-8)
      (strcat "slit axis excludes translation " (itoa parity))))
  (setq reversed (ast:m-test-route (list (ast:m-test-line '(20.0 60.0) '(20.0 30.0))) nil)
        result (ast:m-test-map line reversed 1 T))
  (ast:m-test (and (ast:g-get 'ok result nil) (ast:g-get 'reversed (car (ast:g-get 'pairs result nil)) nil)
    (equal (ast:g-get 'phase (car (ast:g-get 'pairs result nil)) nil) 30.0 1e-8)) "selected matching end determines reverse traversal and phase")
  (ast:m-test (equal (ast:m-point '(4.0 2.0) (ast:g-get 'transform result nil)) '(18.0 34.0) 1e-8)
    "reversed native line retains the chosen physical registration")
  (setq split (ast:m-test-route (list (ast:m-test-line '(20.0 30.0) '(20.0 39.0)) (ast:m-test-line '(20.0 39.0) '(20.0 60.0))) nil))
  (ast:m-test (ast:g-get 'ok (ast:m-test-map line split 1 nil) nil) "line matches redundant polyline vertices")
  (ast:m-test (ast:g-get 'ok (ast:m-test-map split line 1 nil) nil) "redundant source vertices match unsplit target")
  (ast:m-test (not (ast:g-get 'ok (ast:m-test-map line (ast:m-test-route (list (ast:m-test-line '(20.0 30.0) '(20.0 60.01))) nil) 1 nil) nil))
    "length change refuses without scaling")
  (ast:m-test (not (ast:g-get 'ok (ast:m-map-routes (list line) (list target) 0 nil nil nil) nil)) "invalid face refuses")
  (ast:m-test (not (ast:g-get 'ok (ast:m-map-routes (list line) (list target) 1 nil 31.0 nil) nil)) "registration outside guide refuses")
  (ast:m-test (not (ast:g-get 'ok (ast:m-map-routes (list line) nil 1 nil nil nil) nil)) "missing target refuses")

  (setq arc (ast:m-test-route (list (ast:m-test-arc '(0.0 0.0) 10.0 0.0 (/ pi 2.0))) nil)
        target (ast:m-test-route (list (ast:m-test-arc '(20.0 30.0) 10.0 (/ pi 2.0) (/ pi 2.0))) nil)
        reversed (ast:m-test-route (list (ast:m-test-arc '(20.0 30.0) 10.0 (/ pi 2.0) (- (/ pi 2.0)))) nil))
  (ast:m-test (ast:g-get 'ok (ast:m-test-map arc target 1 nil) nil) "arc quarter-turn registration")
  (ast:m-test (ast:g-get 'ok (ast:m-test-map arc reversed -1 nil) nil) "reflection reverses positive arc winding")
  (ast:m-test (ast:g-get 'ok (ast:m-test-map reversed arc -1 nil) nil) "reflection reverses negative arc winding")
  (ast:m-test (not (ast:g-get 'ok (ast:m-test-map arc reversed 1 nil) nil)) "wrong face cannot change arc curvature")
  (setq split (ast:m-test-route (list (ast:m-test-arc '(20.0 30.0) 10.0 (/ pi 2.0) (/ pi 6.0))
                                    (ast:m-test-arc '(20.0 30.0) 10.0 (* pi (/ 2.0 3.0)) (/ pi 3.0))) nil))
  (ast:m-test (ast:g-get 'ok (ast:m-test-map arc split 1 nil) nil) "co-circular subdivisions match analytically")
  (ast:m-test (not (ast:g-get 'ok (ast:m-test-map arc (ast:m-test-route (list (ast:m-test-arc '(20.0 30.0) 10.01 (/ pi 2.0) (/ pi 2.0))) nil) 1 nil) nil))
    "changed arc radius refuses")
  (setq source (ast:m-test-route (list (ast:m-test-line '(-20.0 0.0) '(0.0 0.0))
                  (ast:m-test-arc '(0.0 10.0) 10.0 (- (/ pi 2.0)) (/ pi 2.0))) nil)
        target (ast:m-test-route (list (ast:m-test-line '(20.0 10.0) '(20.0 30.0))
                  (ast:m-test-arc '(10.0 30.0) 10.0 0.0 (/ pi 2.0))) nil))
  (ast:m-test (ast:g-get 'ok (ast:m-test-map source target 1 nil) nil) "mixed line-arc polyline matches")

  (setq circle (ast:m-test-route (list (ast:m-test-arc '(0.0 0.0) 10.0 0.0 (* 2.0 pi))) T)
        target-circle (ast:m-test-route (list (ast:m-test-arc '(20.0 30.0) 10.0 0.0 (* 2.0 pi))) T)
        result (ast:m-map-routes (list circle) (list target-circle) 1 nil 0.0 (* 5.0 pi)))
  (ast:m-test (and (ast:g-get 'ok result nil)
    (equal (ast:m-point '(10.0 0.0) (ast:g-get 'transform result nil)) '(20.0 40.0) 1e-8)
    (equal (ast:g-get 'phase (car (ast:g-get 'pairs result nil)) nil) (* 5.0 pi) 1e-8)) "circle registration fixes physical stitch phase")
  (setq result (ast:m-map-routes (list circle) (list target-circle) -1 T 0.0 (* 5.0 pi)))
  (ast:m-test (and (ast:g-get 'ok result nil)
    (equal (ast:m-point '(0.0 10.0) (ast:g-get 'transform result nil)) '(30.0 30.0) 1e-8)) "opposite circle face preserves registered start and reverses winding")
  (ast:m-test (not (ast:g-get 'ok (ast:m-map-routes (list circle) (list target-circle) -1 nil nil nil) nil))
    "circle target direction must agree with opposite face")
  (ast:m-test (not (ast:g-get 'ok (ast:m-test-map circle (ast:n-put 'closed nil target-circle) 1 nil) nil)) "open and closed guide topology differs")
  (setq square (ast:m-test-route (list (ast:m-test-line '(0.0 0.0) '(10.0 0.0)) (ast:m-test-line '(10.0 0.0) '(10.0 10.0))
                    (ast:m-test-line '(10.0 10.0) '(0.0 10.0)) (ast:m-test-line '(0.0 10.0) '(0.0 0.0))) T)
        target-square (ast:m-test-route (list (ast:m-test-line '(20.0 40.0) '(10.0 40.0)) (ast:m-test-line '(10.0 40.0) '(10.0 30.0))
                    (ast:m-test-line '(10.0 30.0) '(20.0 30.0)) (ast:m-test-line '(20.0 30.0) '(20.0 40.0))) T)
        result (ast:m-map-routes (list square) (list target-square) 1 nil 0.0 30.0))
  (ast:m-test (and (ast:g-get 'ok result nil) (equal (ast:m-point '(2.0 3.0) (ast:g-get 'transform result nil)) '(17.0 32.0) 1e-8))
    "closed polyline uses selected phase rather than arbitrary entity seam")
  (setq result (ast:m-map-routes (list square) (list target-square) 1 nil 5.0 35.0))
  (ast:m-test (and (ast:g-get 'ok result nil) (equal (ast:m-point '(2.0 3.0) (ast:g-get 'transform result nil)) '(17.0 32.0) 1e-8))
    "interior closed-guide registration splits analytical spans")

  (setq line (ast:m-test-route (list (ast:m-test-line '(-30.0 0.0) '(30.0 0.0))) nil)
        branch (ast:m-test-route (list (ast:m-test-line '(0.0 0.0) '(0.0 20.0))) nil)
        lower (ast:m-test-route (list (ast:m-test-line '(0.0 0.0) '(0.0 -15.0))) nil)
        paths (list line branch lower)
        targets (list (ast:m-test-route (list (ast:m-test-line '(20.0 0.0) '(20.0 60.0))) nil)
                      (ast:m-test-route (list (ast:m-test-line '(35.0 30.0) '(20.0 30.0))) nil)
                      (ast:m-test-route (list (ast:m-test-line '(20.0 30.0) '(0.0 30.0))) nil))
        result (ast:m-map-routes paths targets 1 nil nil nil))
  (ast:m-test (and (ast:g-get 'ok result nil) (equal (mapcar '(lambda (item) (ast:g-get 'target-index item nil)) (ast:g-get 'pairs result nil)) '(0 2 1)))
    "connected group identifies reordered members under one common placement")
  (setq pair (nth 2 (ast:g-get 'pairs result nil)))
  (ast:m-test (and (ast:g-get 'reversed pair nil) (equal (ast:g-get 'phase pair nil) 15.0 1e-8)) "nonregistration member detects reversed native traversal")
  (setq changed (list (car targets) (cadr targets) (ast:m-test-route (list (ast:m-test-line '(20.01 30.0) '(0.01 30.0))) nil)))
  (ast:m-test (not (ast:g-get 'ok (ast:m-map-routes paths changed 1 nil nil nil) nil)) "independently displaced branch refuses")
  (ast:m-test (not (ast:g-get 'ok (ast:m-map-routes paths (list (car targets) (caddr targets) (caddr targets)) 1 nil nil nil) nil))
    "duplicate target member refuses ambiguous correspondence")

  ;; This reported shallow corner needs an adjusted construction step. Copy its
  ;; solved openings, including the off-guide round hole, rather than fitting again.
  (setq source (ast:m-test-route (list (ast:m-test-line '(-38.0 258.0) '(107.80342046542515 215.04231639645309))
                                     (ast:m-test-line '(107.80342046542515 215.04231639645309) '(285.06457440910435 231.24365283994626))) nil)
        settings '((pitch . 3.0) (slit-length . 1.5) (lean . 0.6981317007977318) (thickness . 0.2) (margin . 0.2))
        solution (ast:g-solve source settings nil) original solution)
  (ast:m-test (and (ast:g-get 'ok solution nil) (= 1 (length (ast:g-get 'corner-adjustments solution nil)))) "source shallow corner has one known adjustment")
  (foreach parity '(1 -1)
    (setq transform (list '(origin 0.0 0.0) '(target 20.0 30.0) '(old-axis 1.0 0.0) '(new-axis 0.0 1.0) (cons 'parity parity))
          copy (ast:m-solution solution transform) index 0)
    (ast:m-test (and (= (length (ast:g-get 'openings solution nil)) (length (ast:g-get 'openings copy nil)))
      (= (ast:g-get 'status copy nil) 'adjusted)) (strcat "copy preserves hole count and adjustment status " (itoa parity)))
    (foreach source-opening (ast:g-get 'openings solution nil)
      (setq target-opening (nth index (ast:g-get 'openings copy nil)))
      (ast:m-test (and (= (ast:g-get 'type source-opening nil) (ast:g-get 'type target-opening nil))
        (equal (ast:g-get 'center target-opening nil) (ast:m-test-expected (ast:g-get 'center source-opening nil) parity) 1e-8)
        (if (= (ast:g-get 'type source-opening nil) 'slit)
          (and (equal (ast:g-get 'axis target-opening nil) (list (* (- parity) (cadr (ast:g-get 'axis source-opening nil))) (car (ast:g-get 'axis source-opening nil))) 1e-8)
               (= (ast:g-get 'length source-opening nil) (ast:g-get 'length target-opening nil)))
          (= (ast:g-get 'diameter source-opening nil) (ast:g-get 'diameter target-opening nil))))
        (strcat "exact transferred opening " (itoa parity) "/" (itoa index)))
      (setq index (1+ index)))
    (ast:m-test (null (ast:g-validate-openings (ast:g-get 'openings copy nil) settings)) (strcat "rigid copy preserves physical clearance " (itoa parity)))
    (ast:m-test (and (= (length (ast:g-get 'virtual-slits copy nil)) 2)
      (equal (ast:g-get 'center (car (ast:g-get 'virtual-slits copy nil)) nil)
             (ast:m-test-expected (ast:g-get 'center (car (ast:g-get 'virtual-slits solution nil)) nil) parity) 1e-8))
      (strcat "virtual slits follow physical copy " (itoa parity)))
    (ast:m-test (equal (ast:g-get 'virtual-center (car (ast:g-get 'corner-adjustments copy nil)) nil)
                      (ast:m-test-expected (ast:g-get 'virtual-center (car (ast:g-get 'corner-adjustments solution nil)) nil) parity) 1e-8)
      (strcat "construction adjustment notation follows copy " (itoa parity)))
    (setq index 0)
    (foreach interval (ast:g-get 'intervals solution nil)
      (setq expected (nth index (ast:g-get 'intervals copy nil)))
      (ast:m-test (and (= (ast:g-get 'primitive interval nil) (ast:g-get 'primitive expected nil))
        (= (ast:g-get 'kind interval nil) (ast:g-get 'kind expected nil))
        (if (assoc 'from interval)
          (and (equal (ast:g-get 'from expected nil) (ast:m-test-expected (ast:g-get 'from interval nil) parity) 1e-8)
               (equal (ast:g-get 'to expected nil) (ast:m-test-expected (ast:g-get 'to interval nil) parity) 1e-8))
          (equal interval expected))) (strcat "interval classification and coordinates " (itoa parity) "/" (itoa index)))
      (setq index (1+ index))))
  (ast:m-test (equal solution original) "copy does not mutate the source solution")
  (setq inverse (list (cons 'origin (ast:g-get 'target transform nil)) (cons 'target (ast:g-get 'origin transform nil))
                     (cons 'old-axis (ast:g-get 'new-axis transform nil)) (cons 'new-axis (ast:g-get 'old-axis transform nil))
                     (cons 'parity (ast:g-get 'parity transform nil))))
  (ast:m-test (equal (ast:m-solution copy inverse) solution 1e-8) "inverse reflection restores complete shallow-corner solution")

  (setq connection (list '(id . 8) '(point 0.0 0.0)
                     (cons 'incidences (list (list '(path . 0) '(primitive . 0) '(station . 30.0) (cons 'source-route line))
                                            (list '(path . 1) '(primitive . 0) '(station . 0.0) (cons 'source-route branch)))))
        source (list '(ok . T) (cons 'connections (list connection)))
        copy (ast:m-solution source transform) connection (car (ast:g-get 'connections copy nil)))
  (ast:m-test (and (= (ast:g-get 'id connection nil) 8) (equal (ast:g-get 'point connection nil) '(20.0 30.0) 1e-8)
    (= 2 (length (ast:g-get 'incidences connection nil)))) "shared connection identity and incidence count survive reflection")
  (setq incidence (car (ast:g-get 'incidences connection nil)))
  (ast:m-test (and (= (ast:g-get 'station incidence nil) 30.0) (= (ast:g-get 'path incidence nil) 0)
    (equal (ast:g-point (car (ast:g-get 'primitives (ast:g-get 'source-route incidence nil) nil)) 0.0) '(20.0 0.0) 1e-8))
    "saved connection attachment geometry transforms without changing stations")
  (setq paths (list (list '(id . 0) (cons 'route line) (cons 'settings settings))
                    (list '(id . 1) (cons 'route branch) (cons 'settings settings)))
        connection (ast:g-get 'connections (ast:g-connect-candidates line branch) nil)
        solution (ast:g-solve-set paths connection) copy (ast:m-solution solution transform))
  (ast:m-test (and (ast:g-get 'ok solution nil)
    (= 1 (length (vl-remove-if-not '(lambda (opening) (= (ast:g-get 'type opening nil) 'round)) (ast:g-get 'openings copy nil)))))
    "actual connected T copy keeps exactly one shared round hole")
  (ast:m-test (and (= (length (ast:g-get 'openings solution nil)) (length (ast:g-get 'openings copy nil)))
    (equal (ast:m-solution copy inverse) solution 1e-8)) "connected T round trip retains openings and saved junction attachments")
  (list (cons 'ok (null ast:m-test-failures)) (cons 'checks ast:m-test-count) (cons 'failures (reverse ast:m-test-failures))))
(princ)
