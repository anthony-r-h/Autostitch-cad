;;; Native integration checks; use a disposable drawing and load the CAD test helpers.
(defun ast:match-test-line (aa bb)
  (entmakex (list '(0 . "LINE") '(8 . "0") (cons 10 (append aa '(0.0))) (cons 11 (append bb '(0.0))))))
(defun ast:match-test-openings (output / entity data aa bb delta size result)
  (if (and output (entget output))
    (progn
      (setq entity (tblobjname "BLOCK" (cdr (assoc 2 (entget output)))))
      (while (and (setq entity (entnext entity)) (/= (cdr (assoc 0 (setq data (entget entity)))) "ENDBLK"))
        (if (= (cdr (assoc 8 data)) "AUTOSTITCH")
          (cond
            ((and (= (cdr (assoc 0 data)) "LINE") (= (cdr (assoc 370 data)) 30))
              (setq aa (ast:cad-xy (cdr (assoc 10 data)) 1.0) bb (ast:cad-xy (cdr (assoc 11 data)) 1.0)
                    delta (ast:g-sub bb aa) size (ast:g-norm delta)
                    result (cons (list '(type . slit) (cons 'center (ast:g-mul (ast:g-add aa bb) 0.5))
                      (cons 'axis (ast:g-mul delta (/ 1.0 size))) (cons 'length size)) result)))
            ((= (cdr (assoc 0 data)) "CIRCLE")
              (setq result (cons (list '(type . round) (cons 'center (ast:cad-xy (cdr (assoc 10 data)) 1.0))
                (cons 'diameter (* 2.0 (cdr (assoc 40 data))))) result)))))))) result)
(defun ast:match-test-output (source target transform / aa bb)
  (setq aa (ast:match-test-openings source) bb (ast:match-test-openings target))
  (and aa (= (length aa) (length bb))
    (vl-every '(lambda (opening) (vl-some '(lambda (other) (ast:match-test-same (ast:m-opening opening transform) other)) bb)) aa)))
(defun ast:match-test-same (aa bb)
  ;; Length reconstructed from DWG endpoints carries coordinate subtraction roundoff.
  (and (eq (ast:cad-get 'type aa) (ast:cad-get 'type bb))
    (< (ast:g-dist (ast:cad-get 'center aa) (ast:cad-get 'center bb)) 1e-7)
    (if (eq (ast:cad-get 'type aa) 'slit)
      (and (< (abs (- (ast:cad-get 'length aa) (ast:cad-get 'length bb))) 1e-8)
        (< (abs (ast:g-cross (ast:cad-get 'axis aa) (ast:cad-get 'axis bb))) 1e-8))
      (< (abs (- (ast:cad-get 'diameter aa) (ast:cad-get 'diameter bb))) 1e-8))))
(defun ast:match-test-transform (source target parity reversed phase / mapping)
  (setq mapping (ast:m-map-routes (list (ast:cad-get 'route (ast:cad-read-base source)))
    (list (ast:cad-get 'route (ast:cad-read-base target))) parity reversed nil phase))
  (ast:cad-get 'transform mapping))
(defun ast:match-test-record (entity record / ast:*cad-key*)
  (setq ast:*cad-key* "AUTOSTITCH_MATCH_V1")
  (ast:cad-write-record entity (vl-remove-if '(lambda (item) (eq (car item) 'link)) record) (ast:cad-get 'link record)))

(defun ast:match-name-tests (/ settings source first second third result prefix output record old-id block guide)
  (ast:cad-test-assert (equal '("A" "Z" "AA" "AZ" "BA" "ZZ" "AAA")
    (mapcar 'ast:match-suffix '(1 26 27 52 53 702 703)))
    "Matching suffixes continue from Z to AA and from ZZ to AAA")
  (ast:cad-test-assert (and
    (equal '(10 10 10 10) (mapcar 'ast:cad-id-number '("ST-10" "ST-10-A" "ST-10-AA" "ST-10-A-B")))
    (vl-every 'null (mapcar 'ast:cad-id-number '("ST-0-A" "ST-10-" "ST-10-a" "ST-10-A1" "ST-010-A" "ST-10--A"))))
    "Stitch IDs accept letter suffixes while rejecting malformed names")
  (setq settings (ast:cad-default-settings)
        source (ast:match-test-line '(0.0 8000.0) '(30.0 8000.0))
        first (ast:match-test-line '(100.0 8000.0) '(130.0 8000.0))
        second (ast:match-test-line '(200.0 8000.0) '(230.0 8000.0))
        third (ast:match-test-line '(300.0 8000.0) '(330.0 8000.0)))
  (ast:match-link source first 1 nil)
  (ast:match-link source second -1 nil)
  (setq prefix (strcat (ast:cad-stitch-id source) "-"))
  (ast:cad-test-assert (and (= (strcat prefix "A") (ast:cad-stitch-id first))
                          (= (strcat prefix "B") (ast:cad-stitch-id second)))
    "Linked copies receive their source ID with stable A and B suffixes")
  (setq result (ast:cad-generate source settings nil))
  (ast:cad-test-assert (and (ast:cad-get 'ok result)
    (vl-every '(lambda (guide) (and
      (= (ast:cad-stitch-id guide) (cdr (assoc 2 (entget (ast:cad-get 'output (ast:cad-read guide))))))
      (ast:marker-test-id guide (ast:marker-test-entities (ast:markers-reference guide))))) (list first second)))
    "Matching copy block names and boxed labels agree with their suffixed IDs")
  (ast:match-unlink first)
  (setq result (ast:match-link source third 1 nil))
  (ast:cad-test-assert (and (ast:cad-get 'ok result)
    (= (strcat prefix "A") (ast:cad-stitch-id first)) (= (strcat prefix "B") (ast:cad-stitch-id second))
    (= (strcat prefix "C") (ast:cad-stitch-id third)))
    "Unlinking a copy preserves its ID and never renumbers or reuses a live sibling ID")
  ;; Simulate the older independent name on a linked copy, preserving its physical output.
  (setq output (ast:cad-get 'output (ast:cad-read second)) old-id (ast:cad-next-stitch-id)
        block (vla-Item (vla-get-Blocks (vla-get-ActiveDocument (vlax-get-acad-object))) (cdr (assoc 2 (entget output)))))
  (vla-put-Name block old-id)
  (foreach guide (list second output)
    (setq record (ast:cad-record guide))
    (ast:cad-write-record guide (ast:cad-put 'stitch-id old-id
      (vl-remove-if '(lambda (item) (eq (car item) 'link)) record)) (ast:cad-get 'link record)))
  (setq result (ast:cad-generate source settings nil))
  (ast:cad-test-assert (and (ast:cad-get 'ok result) (= (strcat prefix "B") (ast:cad-stitch-id second))
    (= (strcat prefix "B") (cdr (assoc 2 (entget output)))))
    "Regeneration migrates existing linked copies from independent IDs to family block names")
  (setq source (ast:match-test-line '(0.0 8100.0) '(30.0 8100.0))
        first (ast:match-test-line '(100.0 8100.0) '(130.0 8100.0)))
  (ast:cad-save-inputs source settings nil)
  (setq prefix (strcat (ast:cad-stitch-id source) "-"))
  (entmake (list '(0 . "BLOCK") (cons 2 (strcat prefix "A")) '(70 . 0) '(10 0.0 0.0 0.0)))
  (entmake '((0 . "ENDBLK")))
  (setq result (ast:match-link source first 1 nil))
  (ast:cad-test-assert (and (ast:cad-get 'ok result) (= (strcat prefix "B") (ast:cad-stitch-id first)))
    "Matching IDs skip an existing unrelated block name without replacing it"))

(defun ast:match-stitch-tests (/ settings source target first second result source-output target-output signature transform before)
  (setq settings (ast:cad-default-settings)
        source (ast:match-test-line '(0.0 8300.0) '(30.0 8300.0))
        target (ast:match-test-line '(100.0 8300.0) '(130.0 8300.0)))
  (ast:match-link source target -1 nil)
  (ast:cad-generate source settings nil)
  (setq source-output (ast:cad-get 'output (ast:cad-read source))
        target-output (ast:cad-get 'output (ast:cad-read target))
        signature (ast:cad-output-signature source-output)
        result (ast:cad-set-stitch source -1))
  (ast:cad-test-assert (and (ast:cad-get 'ok result)
    (= 1 (ast:cad-get 'face (ast:match-info source))) (= -1 (ast:cad-get 'face (ast:match-info target)))
    (ast:cad-get 'stale (ast:cad-read source)) (ast:cad-get 'stale (ast:cad-read target))
    (equal signature (ast:cad-output-signature source-output)))
    "Changing stitch lean preserves material faces and output while marking the matching family stale")
  (vl-cmdf "_.UNDO" 1)
  (ast:cad-test-assert (= 1 (ast:g-get 'stitch-hand (ast:cad-get 'settings (ast:cad-read source)) 1))
    "One Undo restores the source stitch lean")
  (vl-cmdf "_.REDO")
  (ast:cad-test-assert (= -1 (ast:g-get 'stitch-hand (ast:cad-get 'settings (ast:cad-read source)) 1))
    "Redo restores the reverse stitch choice")
  (setq result (ast:cad-generate target nil nil) transform (ast:match-test-transform source target -1 nil nil))
  (ast:cad-test-assert (and (ast:cad-get 'ok result)
    (= -1 (ast:cad-get 'stitch-hand (ast:cad-get 'settings (ast:cad-read target))))
    (not (equal signature (ast:cad-output-signature source-output)))
    (ast:match-test-output source-output target-output transform))
    "A reflected matching copy inherits reverse stitch lean and the exact source layout")
  (setq before (ast:cad-record target) result (ast:cad-set-stitch target 1))
  (ast:cad-test-assert (and (not (ast:cad-get 'ok result)) (equal before (ast:cad-record target)))
    "A matching copy rejects an independent stitch lean edit without changing metadata")
  (setq signature (ast:cad-output-signature source-output))
  (ast:cad-set-stitch source 1)
  (setq before (ast:cad-record source) ast:*cad-fail-stage* "match-copy-output"
        result (ast:cad-generate target nil nil) ast:*cad-fail-stage* nil)
  (ast:cad-test-assert (and (not (ast:cad-get 'ok result)) (equal before (ast:cad-record source))
    (equal signature (ast:cad-output-signature source-output)))
    "Failed generation after a stitch lean edit retains the previous output and pending choice")
  (setq first (ast:match-test-line '(0.0 8400.0) '(15.0 8400.0))
        second (ast:match-test-line '(15.0 8400.0) '(30.0 8400.0)))
  (ast:cad-save-inputs first (vl-remove-if '(lambda (item) (eq (car item) 'stitch-hand)) settings) nil)
  (setq result (ast:cad-connect-guides first second nil settings nil))
  (ast:cad-test-assert (ast:cad-get 'ok result) "Legacy obverse settings connect to explicit obverse settings")
  (setq result (ast:cad-set-stitch second -1))
  (ast:cad-test-assert (and (ast:cad-get 'ok result)
    (vl-every '(lambda (guide) (= -1 (ast:cad-get 'stitch-hand (ast:cad-get 'settings (ast:cad-read guide))))) (list first second))
    (ast:cad-get 'ok (ast:cad-generate second (ast:cad-get 'settings (ast:cad-read second)) nil)))
    "Changing stitch lean through a secondary guide updates and regenerates the entire connected line"))

(defun ast:match-cad-tests (/ ast:*cad-test-passed* ast:*cad-test-failures* original-units original-copy settings source target third result count source-output target-output transform source-record target-record source-match target-match source-signature target-signature data copy before selection cursor copies copied-source copied-target original-source-output original-target-output info circle-source circle-target phase saved-transform old-target-signature)
  (setq ast:*cad-test-passed* 0 ast:*cad-test-failures* nil original-units (getvar "INSUNITS")
        original-copy (getvar "COPYMODE") settings (ast:cad-default-settings))
  (setvar "INSUNITS" 4)
  (setq source (ast:match-test-line '(0.0 4000.0) '(30.0 4000.0))
        target (ast:match-test-line '(130.0 4040.0) '(100.0 4040.0))
        count (ast:cad-test-inserts) result (ast:match-link source target -1 T))
  (ast:cad-test-assert (and (ast:cad-get 'ok result) (= count (ast:cad-test-inserts))
    (eq (ast:cad-get 'role (ast:match-info source)) 'source)
    (eq (ast:cad-get 'role (ast:match-info target)) 'copy)
    (/= (ast:cad-stitch-id source) (ast:cad-stitch-id target)))
    "Matching pieces saves separate stitch IDs and reciprocal ownership without creating output")
  (setq result (ast:cad-generate target (ast:cad-put 'pitch 9.0 settings) nil)
        source-output (ast:cad-get 'output (ast:cad-read source)) target-output (ast:cad-get 'output result)
        transform (ast:match-test-transform source target -1 T nil))
  (ast:cad-test-assert (and (ast:cad-get 'ok result) (= 11 (length (ast:match-test-openings source-output)))
    (ast:match-test-output source-output target-output transform)
    (not (ast:cad-get 'stale (ast:cad-read source))) (not (ast:cad-get 'stale (ast:cad-read target))))
    "Generate from a matching copy ignores its draft and transfers the source holes exactly")
  (setq source-match (ast:match-record source) target-match (ast:match-record target)
        source-signature (ast:cad-output-signature source-output) target-signature (ast:cad-output-signature target-output))
  (ast:match-test-record source '((schema . -1)))
  (setq result (ast:cad-generate source settings nil))
  (ast:cad-test-assert (and (not (ast:cad-get 'ok result)) (ast:cad-get 'active (ast:match-info source))
    (equal source-signature (ast:cad-output-signature source-output)) (equal target-signature (ast:cad-output-signature target-output)))
    "Malformed association metadata without an identity cannot silently generate as an independent line")
  (ast:match-write-group source source-match)
  (ast:match-test-record target (ast:cad-put 'schema 2 target-match))
  (setq result (ast:cad-generate source settings nil))
  (ast:cad-test-assert (and (not (ast:cad-get 'ok result))
    (equal source-signature (ast:cad-output-signature source-output)) (equal target-signature (ast:cad-output-signature target-output)))
    "An unknown copy metadata version blocks family generation and preserves both outputs")
  (ast:match-write-group target target-match)
  (setq result (ast:cad-save-inputs target (ast:cad-put 'pitch 4.0 settings) nil))
  (ast:cad-test-assert (not (ast:cad-get 'ok result)) "Matching copies reject independent input edits")
  (setq third (ast:match-test-line '(30.0 4000.0) '(30.0 4030.0))
        result (ast:cad-connect-guides source third nil settings nil))
  (ast:cad-test-assert (not (ast:cad-get 'ok result)) "Connected topology cannot change while a stitch line has matching copies")
  (setq settings (ast:cad-put 'pitch 3.38 settings) result (ast:cad-save-inputs source settings nil))
  (ast:cad-test-assert (and (ast:cad-get 'ok result) (ast:cad-get 'stale (ast:cad-read source))
    (ast:cad-get 'stale (ast:cad-read target))) "Source recipe changes mark the entire matching set stale")
  (setq result (ast:cad-generate source settings nil))
  (ast:cad-test-assert (and (ast:cad-get 'ok result) (ast:match-test-output source-output target-output transform)
    (equal 3.38 (ast:cad-get 'pitch (ast:cad-get 'settings (ast:cad-read target))) 1e-8))
    "Adjusted source spacing is copied exactly rather than fitted independently")
  (entdel target-output)
  (ast:cad-test-assert (ast:cad-get 'stale (ast:cad-read source)) "Deleting a copy output marks its source stale")
  (entdel target-output)
  (setq source-record (ast:cad-record source) target-record (ast:cad-record target)
        source-match (ast:match-record source) target-match (ast:match-record target)
        source-signature (ast:cad-output-signature source-output) target-signature (ast:cad-output-signature target-output)
        data (entget target))
  (entmod (subst '(11 99.0 4040.0 0.0) (assoc 11 data) data))
  (setq result (ast:cad-generate source settings nil))
  (ast:cad-test-assert (and (not (ast:cad-get 'ok result))
    (equal source-signature (ast:cad-output-signature source-output)) (equal target-signature (ast:cad-output-signature target-output))
    (equal source-record (ast:cad-record source)) (equal target-record (ast:cad-record target)))
    "An incongruent matching guide rejects the entire generation without changing output")
  (entmod data)
  (setq ast:*cad-fail-stage* "match-copy-output"
        result (ast:cad-generate source (ast:cad-put 'pitch 2.7 settings) nil) ast:*cad-fail-stage* nil)
  (ast:cad-test-assert (and (not (ast:cad-get 'ok result))
    (equal source-signature (ast:cad-output-signature source-output)) (equal target-signature (ast:cad-output-signature target-output))
    (equal source-record (ast:cad-record source)) (equal target-record (ast:cad-record target))
    (equal source-match (ast:match-record source)) (equal target-match (ast:match-record target)))
    "Failure after writing a copy rolls back every source, output and association record")
  (setq result (ast:match-set-face target 1))
  (ast:cad-test-assert (and (ast:cad-get 'ok result) (= 1 (ast:cad-get 'face (ast:match-info target)))
    (equal target-signature (ast:cad-output-signature target-output))) "Changing a copy face changes inputs without replacing output")
  (vl-cmdf "_.UNDO" 1)
  (ast:cad-test-assert (= -1 (ast:cad-get 'face (ast:match-info target))) "One Undo restores a matching copy's previous face")
  (vl-cmdf "_.REDO")
  (ast:cad-test-assert (= 1 (ast:cad-get 'face (ast:match-info target))) "Redo restores the matching face change")
  (ast:match-set-face target -1)
  (setq result (ast:match-set-face source -1))
  (ast:cad-test-assert (and (ast:cad-get 'ok result) (= -1 (ast:cad-get 'face (ast:match-info source)))
    (= -1 (ast:cad-get 'face (ast:match-info target))) (= 1 (ast:cad-get 'parity (ast:match-record target))))
    "Changing source face preserves each copy's absolute face and updates relative parity")
  (setq settings (ast:cad-get 'settings (ast:cad-read source)) result (ast:cad-generate source settings nil)
        transform (ast:match-test-transform source target 1 T nil))
  (ast:cad-test-assert (and (ast:cad-get 'ok result) (ast:match-test-output source-output target-output transform))
    "A source face change still produces an exact transformed copy")
  ;; Native copies use translated soft references; isolated copies must not steal the original family.
  (setq source-record (ast:cad-record source) target-record (ast:cad-record target)
        source-signature (ast:cad-output-signature source-output) target-signature (ast:cad-output-signature target-output)
        copy (vlax-vla-object->ename (vla-Copy (vlax-ename->vla-object target))))
  (vla-Move (vlax-ename->vla-object copy) (vlax-3d-point '(0.0 0.0 0.0)) (vlax-3d-point '(0.0 100.0 0.0)))
  (setq result (ast:cad-generate copy (ast:cad-get 'settings (ast:cad-read copy)) nil))
  (ast:cad-test-assert (and (not (ast:cad-get 'active (ast:match-info copy))) (ast:cad-get 'ok result)
    (equal source-record (ast:cad-record source)) (equal target-record (ast:cad-record target))
    (equal source-signature (ast:cad-output-signature source-output)) (equal target-signature (ast:cad-output-signature target-output)))
    "Copying only one matching guide detaches the copy and preserves all original ownership")
  (setq selection (ssadd source (ssadd target (ssadd source-output (ssadd target-output)))) before (entlast) copies nil)
  (setvar "COPYMODE" 1)
  (vl-cmdf "_.COPY" selection "" "_non" '(0.0 0.0 0.0) "_non" '(200.0 200.0 0.0))
  (setq cursor before)
  (while (setq cursor (entnext cursor))
    (setq data (entget cursor))
    (if (and (= "LINE" (cdr (assoc 0 data))) (= "0" (cdr (assoc 8 data))))
      (if (< (car (cdr (assoc 10 data))) 250.0) (setq copied-source cursor) (setq copied-target cursor))))
  (setq result (ast:cad-generate copied-source (ast:cad-get 'settings (ast:cad-read copied-source)) nil))
  (ast:cad-test-assert (and (ast:cad-get 'ok result)
    (equal copied-source (ast:cad-get 'source (ast:match-info copied-target)))
    (/= (ast:cad-stitch-id source) (ast:cad-stitch-id copied-source))
    (equal source-record (ast:cad-record source)) (equal target-record (ast:cad-record target))
    (equal source-signature (ast:cad-output-signature source-output)) (equal target-signature (ast:cad-output-signature target-output)))
    "Copying the complete matching set remaps its links and regenerates independently")
  (entdel target)
  (setq info (ast:match-info source) result (ast:cad-generate source settings nil))
  (ast:cad-test-assert (and (ast:cad-get 'repairable info) (not (ast:cad-get 'ok result))
    (equal source-signature (ast:cad-output-signature source-output)) (entget target-output))
    "Deleting a matching copy blocks generation and retains all previous output")
  (setq result (ast:match-unlink source))
  (ast:cad-test-assert (and (ast:cad-get 'ok result) (not (ast:cad-get 'active (ast:match-info source)))
    (equal source-signature (ast:cad-output-signature source-output)) (entget target-output))
    "Remove missing repairs the source association without deleting the old copy output")
  ;; A loop's registration is fixed when linked; changing its stitch phase must not move that registration.
  (setq settings (ast:cad-default-settings)
        circle-source (entmakex '((0 . "CIRCLE") (8 . "0") (10 0.0 4500.0 0.0) (40 . 20.0)))
        circle-target (entmakex '((0 . "CIRCLE") (8 . "0") (10 100.0 4500.0 0.0) (40 . 20.0)))
        phase 5.0 result (ast:match-link circle-source circle-target 1 (list (cons 'phase phase)))
        saved-transform (ast:match-test-transform circle-source circle-target 1 nil phase)
        result (ast:cad-generate circle-source settings nil)
        source-output (ast:cad-get 'output (ast:cad-read circle-source)))
  (setq target-output (ast:cad-get 'output (ast:cad-read circle-target)) old-target-signature (ast:cad-output-signature target-output)
        settings (ast:cad-put 'phase 1.25 settings) result (ast:cad-generate circle-source settings nil))
  (ast:cad-test-assert (and (ast:cad-get 'ok result) (ast:match-test-output source-output target-output saved-transform)
    (not (equal old-target-signature (ast:cad-output-signature target-output))))
    "Changing source loop start moves matching holes under the original fixed registration")
  (setq result (ast:match-set-face circle-target -1) result (ast:cad-generate circle-target nil nil))
  (ast:cad-test-assert (and (ast:cad-get 'ok result) (ast:cad-get 'target-reversed (ast:match-record circle-target))
    (ast:match-test-output source-output target-output (ast:match-test-transform circle-source circle-target -1 T phase)))
    "A closed copy automatically reverses its native traversal when its face becomes Back")
  (setq result (ast:match-set-face circle-target 1) result (ast:cad-generate circle-target nil nil))
  (ast:cad-test-assert (and (ast:cad-get 'ok result) (not (ast:cad-get 'target-reversed (ast:match-record circle-target)))
    (ast:match-test-output source-output target-output saved-transform))
    "Returning a closed copy to Front restores its original registered layout")
  (setq result (ast:match-unlink circle-target))
  (ast:cad-test-assert (and (ast:cad-get 'ok result) (not (ast:cad-get 'active (ast:match-info circle-target)))
    (not (ast:cad-get 'active (ast:match-info circle-source))) (entget source-output) (entget target-output))
    "Unlinking the last copy leaves both layouts and effective inputs intact")
  (ast:match-name-tests)
  (ast:match-stitch-tests)
  (setvar "INSUNITS" original-units) (setvar "COPYMODE" original-copy)
  (list (cons 'passed ast:*cad-test-passed*) (cons 'failed (length ast:*cad-test-failures*))
    (cons 'failures (reverse ast:*cad-test-failures*))))
(defun ast:match-network-tests (/ ast:*cad-test-passed* ast:*cad-test-failures* settings aa ab ba bb ca cb entity result source-output target-output transform count source-signature target-signature)
  (setq ast:*cad-test-passed* 0 ast:*cad-test-failures* nil settings (ast:cad-default-settings)
        aa (ast:match-test-line '(0.0 4700.0) '(30.0 4700.0)) ab (ast:match-test-line '(30.0 4700.0) '(30.0 4730.0))
        ba (ast:match-test-line '(100.0 4700.0) '(130.0 4700.0)) bb (ast:match-test-line '(130.0 4700.0) '(130.0 4670.0))
        ca (ast:match-test-line '(200.0 4700.0) '(230.0 4700.0)) cb (ast:match-test-line '(230.0 4700.0) '(230.0 4730.0)))
  (ast:cad-connect-guides aa ab nil settings nil)
  (ast:cad-connect-guides ba bb nil settings nil)
  (ast:cad-connect-guides ca cb nil settings nil)
  (ast:cad-save-inputs aa settings '(((primitive . 0) (station . 16.5))))
  (ast:cad-save-inputs ba settings '(((primitive . 0) (station . 20.0))))
  (setq result (ast:match-link ab bb -1 nil))
  (ast:cad-test-assert (and (not (ast:cad-get 'ok result)) (not (ast:cad-get 'active (ast:match-info aa))))
    "Conflicting counterpart landmarks reject matching without discarding either recipe")
  (ast:cad-save-inputs ba settings nil)
  (setq count (ast:cad-test-inserts) result (ast:match-link aa ba -1 nil))
  (ast:cad-test-assert (and (ast:cad-get 'ok result) (= count (ast:cad-test-inserts))
    (equal '(((primitive . 0) (station . 16.5))) (ast:cad-get 'landmarks (ast:cad-read ba)) 1e-7))
    "Whole connected groups match and inherit source landmarks")
  (setq result (ast:match-link ab cb 1 nil))
  (ast:cad-test-assert (and (ast:cad-get 'ok result) (= 1 (ast:cad-get 'source-index (ast:match-record ca)))
    (equal aa (ast:cad-get 'source (ast:match-info ca))))
    "Adding a second connected copy respects the newly selected source registration member")
  (setq result (ast:cad-generate bb nil nil) source-output (ast:cad-get 'output (ast:cad-read aa))
        target-output (ast:cad-get 'output (ast:cad-read ba))
        transform '((origin 0.0 4700.0) (target 100.0 4700.0) (old-axis 1.0 0.0) (new-axis 1.0 0.0) (parity . -1)))
  (ast:cad-test-assert (and (ast:cad-get 'ok result) (= (+ count 3) (ast:cad-test-inserts))
    (ast:match-test-output source-output target-output transform)
    (= (ast:cad-stitch-id aa) (ast:cad-stitch-id ab)) (= (ast:cad-stitch-id ba) (ast:cad-stitch-id bb))
    (/= (ast:cad-stitch-id aa) (ast:cad-stitch-id ba)))
    "Matching connected groups preserves junction holes and owns one distinct output per piece")
  (foreach entity (list ba bb)
    (vla-Move (vlax-ename->vla-object entity) (vlax-3d-point '(0.0 0.0 0.0)) (vlax-3d-point '(40.0 20.0 0.0))))
  (setq result (ast:cad-generate bb nil nil) transform (ast:cad-put 'target '(140.0 4720.0) transform))
  (ast:cad-test-assert (and (ast:cad-get 'ok result) (ast:match-test-output source-output target-output transform)
    (not (ast:cad-get 'stale (ast:cad-read aa))))
    "Moving all guides of a matching piece preserves its mapped landmark and junction recipe")
  (setq source-signature (ast:cad-output-signature source-output) target-signature (ast:cad-output-signature target-output))
  (entdel bb)
  (setq result (ast:cad-generate aa settings (ast:cad-get 'landmarks (ast:cad-read aa))))
  (ast:cad-test-assert (and (not (ast:cad-get 'ok result))
    (equal source-signature (ast:cad-output-signature source-output)) (equal target-signature (ast:cad-output-signature target-output)))
    "A missing connected member blocks matching generation without partial output")
  (setq result (ast:match-unlink ba))
  (ast:cad-test-assert (and (ast:cad-get 'ok result) (equal (list ca) (ast:cad-get 'targets (ast:match-info aa)))
    (not (ast:cad-get 'active (ast:match-info ba))) (entget source-output) (entget target-output))
    "A damaged connected copy can be unlinked before repairing its own guide topology")
  (list (cons 'passed ast:*cad-test-passed*) (cons 'failed (length ast:*cad-test-failures*))
    (cons 'failures (reverse ast:*cad-test-failures*))))

;;; Save the disposable DWG after this returns OK; reload source/tests before running the checks.
(defun ast:match-reopen-fixture (data-path / settings source front back broken-source broken-copy result outputs records stream)
  (setq settings (ast:cad-put 'stitch-hand -1 (ast:cad-default-settings))
        source (ast:match-test-line '(0.0 5000.0) '(30.5 5000.0))
        front (ast:match-test-line '(100.0 5040.0) '(130.5 5040.0))
        back (ast:match-test-line '(200.0 5080.0) '(230.5 5080.0))
        result (ast:match-link source front 1 nil))
  (ast:cad-require (ast:cad-get 'ok result) (ast:cad-get 'error result))
  (setq result (ast:match-link source back -1 nil))
  (ast:cad-require (ast:cad-get 'ok result) (ast:cad-get 'error result))
  (setq result (ast:cad-generate source settings nil))
  (ast:cad-require (ast:cad-get 'ok result) (ast:cad-get 'error result))
  (setq broken-source (ast:match-test-line '(0.0 5140.0) '(30.0 5140.0))
        broken-copy (ast:match-test-line '(100.0 5140.0) '(130.0 5140.0))
        result (ast:match-link broken-source broken-copy 1 nil))
  (ast:cad-require (ast:cad-get 'ok result) (ast:cad-get 'error result))
  (setq result (ast:cad-generate broken-source settings nil))
  (ast:cad-require (ast:cad-get 'ok result) (ast:cad-get 'error result))
  (setq records (list
    (cons 'guides (mapcar '(lambda (guide) (cdr (assoc 5 (entget guide)))) (list source front back broken-source broken-copy)))
    (cons 'outputs (mapcar '(lambda (guide) (cdr (assoc 5 (entget (ast:cad-get 'output (ast:cad-read guide))))))
      (list source front back broken-source broken-copy)))
    (cons 'ids (mapcar 'ast:cad-stitch-id (list source front back broken-source broken-copy)))))
  (entdel broken-copy)
  (setq stream (open data-path "w"))
  (ast:cad-require stream "Could not write matching fixture handles.")
  (prin1 records stream) (close stream)
  (list '(ok . T) (cons 'data-path data-path)))
(defun ast:match-reopen-tests (data-path / ast:*cad-test-passed* ast:*cad-test-failures* stream records guides outputs ids source front back broken-source result info)
  (setq ast:*cad-test-passed* 0 ast:*cad-test-failures* nil stream (open data-path "r"))
  (ast:cad-require stream "Could not read matching fixture handles.")
  (setq records (read (read-line stream))) (close stream)
  (setq guides (mapcar 'handent (ast:cad-get 'guides records)) outputs (mapcar 'handent (ast:cad-get 'outputs records))
        ids (ast:cad-get 'ids records) source (nth 0 guides) front (nth 1 guides) back (nth 2 guides) broken-source (nth 3 guides))
  (ast:cad-test-assert (and (eq (ast:cad-get 'role (ast:match-info source)) 'source)
    (equal source (ast:cad-get 'source (ast:match-info front))) (equal source (ast:cad-get 'source (ast:match-info back)))
    (= 1 (ast:cad-get 'face (ast:match-info front))) (= -1 (ast:cad-get 'face (ast:match-info back)))
    (equal (list (nth 0 ids) (nth 1 ids) (nth 2 ids)) (mapcar 'ast:cad-stitch-id (list source front back))))
    "Saved matching sets reopen with reciprocal ownership, absolute faces and stable stitch IDs")
  (ast:cad-test-assert (vl-every '(lambda (guide) (not (ast:cad-get 'stale (ast:cad-read guide)))) (list source front back))
    "A saved matching set remains current after reopening")
  (ast:cad-test-assert (vl-every '(lambda (guide)
    (= -1 (ast:cad-get 'stitch-hand (ast:cad-get 'settings (ast:cad-read guide))))) (list source front back))
    "Save and reopen preserve reverse stitch lean independently of the matching faces")
  (setq result (ast:cad-generate source (ast:cad-put 'pitch 3.38 (ast:cad-get 'settings (ast:cad-read source))) nil))
  (ast:cad-test-assert (and (ast:cad-get 'ok result)
    (ast:match-test-output (nth 0 outputs) (nth 1 outputs) (ast:match-test-transform source front 1 nil nil))
    (ast:match-test-output (nth 0 outputs) (nth 2 outputs) (ast:match-test-transform source back -1 nil nil)))
    "Reopened matching sets regenerate both faces from the one source solution")
  (setq info (ast:match-info broken-source) result (ast:cad-generate broken-source (ast:cad-default-settings) nil))
  (ast:cad-test-assert (and (ast:cad-get 'repairable info) (not (ast:cad-get 'ok result))
    (entget (nth 3 outputs)) (entget (nth 4 outputs)))
    "A deleted copy survives save/reopen as a repairable missing reference without deleting output")
  (setq result (ast:match-unlink broken-source))
  (ast:cad-test-assert (and (ast:cad-get 'ok result) (not (ast:cad-get 'active (ast:match-info broken-source)))
    (entget (nth 3 outputs)) (entget (nth 4 outputs)))
    "Remove missing repairs an erased copy reference after save/reopen")
  (entdel front)
  (setq result (ast:match-unlink source))
  (ast:cad-test-assert (and (ast:cad-get 'ok result) (equal (list back) (ast:cad-get 'targets (ast:match-info source)))
    (equal source (ast:cad-get 'source (ast:match-info back))) (entget (nth 1 outputs)))
    "Removing one missing copy keeps healthy matching copies and the old missing-piece output")
  (setq result (ast:cad-generate back nil nil))
  (ast:cad-test-assert (and (ast:cad-get 'ok result)
    (ast:match-test-output (nth 0 outputs) (nth 2 outputs) (ast:match-test-transform source back -1 nil nil)))
    "Healthy copies regenerate normally after missing-copy repair")
  (list (cons 'passed ast:*cad-test-passed*) (cons 'failed (length ast:*cad-test-failures*))
    (cons 'failures (reverse ast:*cad-test-failures*))))
(princ)
