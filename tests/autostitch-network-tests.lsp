;;; Pure network tests. Load geometry and network first; (ast:n-tests) touches no CAD.
(defun ast:n-test (condition label)
  (setq ast:n-test-count (1+ ast:n-test-count))
  (if (not condition) (setq ast:n-test-failures (cons label ast:n-test-failures))))
(defun ast:n-test-line (aa bb) (list '(kind . line) (cons 'a aa) (cons 'b bb)))
(defun ast:n-test-path (id primitives settings)
  (list (cons 'id id) (cons 'route (list (cons 'primitives primitives))) (cons 'settings settings) '(landmarks)))
(defun ast:n-test-connections (aa bb)
  (ast:g-get 'connections (ast:g-connect-candidates (ast:g-get 'route aa nil) (ast:g-get 'route bb nil)) nil))
(defun ast:n-test-rounds (result)
  (vl-remove-if-not '(lambda (opening) (= (ast:g-get 'type opening nil) 'round)) (ast:g-get 'openings result nil)))
(defun ast:n-test-same-cuts (aa bb)
  (and (ast:g-get 'ok aa nil) (ast:g-get 'ok bb nil)
    (= (length (ast:g-get 'openings aa nil)) (length (ast:g-get 'openings bb nil)))
    (vl-every '(lambda (opening) (vl-some '(lambda (other) (ast:g-same-opening opening other)) (ast:g-get 'openings bb nil))) (ast:g-get 'openings aa nil))))
(defun ast:n-test-shift-primitive (primitive delta)
  (if (= (ast:g-get 'kind primitive nil) 'line)
    (ast:n-put 'a (ast:g-add (ast:g-get 'a primitive nil) delta) (ast:n-put 'b (ast:g-add (ast:g-get 'b primitive nil) delta) primitive))
    (ast:n-put 'center (ast:g-add (ast:g-get 'center primitive nil) delta) primitive)))
(defun ast:n-test-shift-path (path delta / route primitives)
  (setq route (ast:g-get 'route path nil) primitives (mapcar '(lambda (primitive) (ast:n-test-shift-primitive primitive delta)) (ast:g-get 'primitives route nil)))
  (ast:n-put 'route (ast:n-put 'primitives primitives route) path))
(defun ast:n-test-remap (connections old-id new-id / node inc result incidences)
  (foreach node connections
    (setq incidences nil)
    (foreach inc (ast:g-get 'incidences node nil)
      (setq incidences (append incidences (list (if (= (ast:g-get 'path inc nil) old-id) (ast:n-put 'path new-id inc) inc)))))
    (setq result (append result (list (ast:n-put 'incidences incidences node))))) result)
(defun ast:n-test-joint-guide (radius winding angle extent incoming / center radial start)
  ;; Analytic fixture construction: tangent angle is measured at the origin.
  (if (= radius 0.0)
    (if incoming (ast:n-test-line (list (* (- extent) (cos angle)) (* (- extent) (sin angle))) '(0.0 0.0))
      (ast:n-test-line '(0.0 0.0) (list (* extent (cos angle)) (* extent (sin angle)))))
    (progn
      (setq center (list (* (- winding) radius (sin angle)) (* winding radius (cos angle)))
            radial (- angle (* winding (/ pi 2.0)))
            start (if incoming (- radial (* winding (/ extent radius))) radial))
      (list '(kind . arc) (cons 'center center) (cons 'radius radius)
        (cons 'start-angle start) (cons 'sweep (* winding (/ extent radius)))))))
(defun ast:n-test-shallow-junctions (settings / fixture incoming outgoing aa bb connections result reference label expected degrees winding extent endpoint angle sweep expected-centers slits)
  ;; Independent tip-locus calculations give these minimum corner steps.
  ;; The last two-arc configuration needs 3.349753725 mm, outside [2.7, 3.3].
  (foreach fixture '((0.0 1 100.0 -1 3.026578361 "line-arc")
                    (100.0 -1 0.0 1 3.203569803 "arc-line")
                    (100.0 -1 80.0 -1 3.081977019 "arc-arc"))
    (setq incoming (ast:n-test-joint-guide (nth 0 fixture) (nth 1 fixture) 0.0 30.0 T)
          outgoing (ast:n-test-joint-guide (nth 2 fixture) (nth 3 fixture) (* pi (/ 21.5 180.0)) 30.0 nil)
          aa (ast:n-test-path 0 (list incoming) settings) bb (ast:n-test-path 1 (list outgoing) settings)
          connections (ast:n-test-connections aa bb) result (ast:g-solve-set (list aa bb) connections)
          reference (ast:g-solve (list (cons 'primitives (list incoming outgoing))) settings nil)
          label (strcat "Shallow connected " (nth 5 fixture)))
    (ast:n-test (and (= 1 (length connections)) (ast:n-test-same-cuts result reference)
      (= 1 (length (ast:n-test-rounds result)))
      (= 1 (length (ast:g-get 'corner-adjustments result nil)))
      (equal (nth 4 fixture) (ast:g-get 'distance (car (ast:g-get 'corner-adjustments result nil)) 0.0) 1e-7))
      (strcat label " matches one route and its independently calculated corner step"))
    (ast:n-test (ast:n-test-same-cuts (ast:g-solve-set (list bb aa) connections) reference)
      (strcat label " keeps the same openings when guide selection is reversed")))
  (setq incoming (ast:n-test-joint-guide 100.0 -1 0.0 30.0 T)
        outgoing (ast:n-test-joint-guide 80.0 1 (* pi (/ 21.5 180.0)) 30.0 nil)
        aa (ast:n-test-path 0 (list incoming) settings) bb (ast:n-test-path 1 (list outgoing) settings)
        connections (ast:n-test-connections aa bb)
        result (ast:g-solve-set (list aa bb) connections))
  (ast:n-test (and (= 1 (length connections)) (not (ast:g-get 'ok result nil))
    (wcmatch (ast:g-get 'error result "") "The corner puts a stitch past the junction*")
    (not (ast:g-get 'ok (ast:g-solve-set (list bb aa) connections) nil))
    (not (ast:g-get 'ok (ast:g-solve (list (cons 'primitives (list incoming outgoing))) settings nil) nil)))
    "Shallow opposite-curvature connected arcs reject the independently required corner step above 3.3 mm")
  ;; Half-pitch arms leave only reserved neighbours: span fitting cannot
  ;; move a collision away. Required slit-axis separation is 0.2 + 0.2 = 0.4 mm.
  ;; Independent slit-edge clearances: T/X 35deg -> .203265473, 30deg -> .128709148.
  ;; At 35deg, R30 curved T gives winding +1 -> .210492762, -1 -> .197195361.
  (foreach fixture '(("T" 35.0 0 T) ("T" 30.0 0 nil)
                    ("X" 35.0 0 T) ("X" 30.0 0 nil)
                    ("curved T" 35.0 1 T) ("curved T" 35.0 -1 nil))
    (setq degrees (nth 1 fixture) winding (nth 2 fixture) expected (nth 3 fixture)
          angle (* pi (/ degrees 180.0))
          aa (ast:n-test-path 0 (list (ast:n-test-line '(-1.5 0.0) '(1.5 0.0))) settings)
          expected-centers '((-1.5 0.0) (1.5 0.0)))
    (if (= winding 0)
      (progn
        (setq endpoint (list (* 1.5 (cos angle)) (* 1.5 (sin angle))))
        (if (= (car fixture) "X")
          (progn
            (setq incoming (list (- (car endpoint)) (- (cadr endpoint)))
                  outgoing (ast:n-test-line incoming endpoint)
                  expected-centers (append expected-centers (list incoming))))
          (setq outgoing (ast:n-test-line '(0.0 0.0) endpoint))))
      (progn
        (setq sweep (* winding 2.0 (atan 1.5 (sqrt (- (* 60.0 60.0) 2.25))))
              extent (* 30.0 (abs sweep))
              outgoing (ast:n-test-joint-guide 30.0 winding angle extent nil)
              endpoint (list (* winding 30.0 (- (sin (+ angle sweep)) (sin angle)))
                             (* winding 30.0 (- (cos angle) (cos (+ angle sweep))))))))
    (setq expected-centers (append expected-centers (list endpoint))
          bb (ast:n-test-path 1 (list outgoing) settings)
          connections (ast:n-test-connections aa bb) result (ast:g-solve-set (list aa bb) connections)
          slits (vl-remove-if-not '(lambda (opening) (= (ast:g-get 'type opening nil) 'slit)) (ast:g-get 'openings result nil))
          label (strcat "Shallow " (car fixture) " at " (rtos degrees 2 0) " degrees winding " (itoa winding)))
    (ast:n-test (if expected
      (and (ast:g-get 'ok result nil) (= 1 (length (ast:n-test-rounds result)))
        (equal '(0.0 0.0) (ast:g-get 'center (car (ast:n-test-rounds result)) nil) 1e-8)
        (= (length expected-centers) (length slits)) (null (ast:g-get 'corner-adjustments result nil))
        (vl-every '(lambda (center) (and (equal 1.5 (distance '(0.0 0.0) center) 1e-8)
          (vl-some '(lambda (opening) (equal center (ast:g-get 'center opening nil) 1e-8)) slits))) expected-centers))
      (and (not (ast:g-get 'ok result nil)) (wcmatch (ast:g-get 'error result "") "Two stitch holes*")))
      (strcat label (if expected " retains every half-pitch first chord and one shared hole" " rejects the independently demonstrated slit-clearance violation")))
    (if expected
      (ast:n-test (ast:n-test-same-cuts result (ast:g-solve-set (list bb aa) connections))
        (strcat label " is unchanged by reversed guide selection")))))
(defun ast:n-test-half-pitch (settings / paths connections degrees id angle arm result firsts intervals)
  (setq id 0)
  (foreach degrees '(0.0 60.0 150.0 225.0 270.0)
    (setq angle (* pi (/ degrees 180.0))
          arm (ast:n-test-path id (list (ast:n-test-line '(0.0 0.0) (list (* 10.5 (cos angle)) (* 10.5 (sin angle))))) settings))
    (if paths (setq connections (append connections (ast:n-test-remap (ast:n-test-connections (car paths) arm) 1 id))))
    (setq paths (append paths (list arm)) id (1+ id)))
  (setq result (ast:g-solve-set paths connections)
        firsts (vl-remove-if-not '(lambda (opening) (and (= 'slit (ast:g-get 'type opening nil))
          (equal 1.5 (ast:g-dist '(0.0 0.0) (ast:g-get 'center opening nil)) 1e-8))) (ast:g-get 'openings result nil))
        intervals (ast:g-get 'intervals result nil))
  (ast:n-test (and (ast:g-get 'ok result nil) (= 1 (length (ast:n-test-rounds result))) (= 5 (length firsts))
    (= 21 (length (ast:g-get 'openings result nil)))
    (vl-every '(lambda (gap) (equal (if (= 'junction (ast:g-get 'kind gap nil)) 1.5 3.0)
      (ast:g-get 'distance gap 0.0) 1e-8)) intervals))
    "Five arms reserve half pitch on every arm and nominal ordinary gaps")
  (ast:n-test (ast:n-test-same-cuts result (ast:g-solve-set (reverse paths) connections))
    "Five-arm half-pitch placement is independent of guide selection order")
  (setq paths (list (ast:n-test-path 0 (list (ast:n-test-line '(-3.0 0.0) '(3.0 0.0))) settings)
                   (ast:n-test-path 1 (list (ast:n-test-line '(0.0 0.0) '(0.0 3.0))) settings))
        result (ast:g-solve-set paths (ast:n-test-connections (car paths) (cadr paths))))
  (ast:n-test (and (not (ast:g-get 'ok result nil)) (null (ast:g-get 'openings result nil)))
    "Short branch spans reject instead of falling back to full pitch"))
(defun ast:n-test-curved-link (settings / old-chord sweep start end mid arc paths connections primitive arm id result slits tangent-hits)
  (foreach old-chord '(nil T)
    (setq sweep (if old-chord (* 2.0 (ast:g-asin 0.05)) (* 4.0 (ast:g-asin 0.025)))
          start '(30.0 0.0) end (list (* 30.0 (cos sweep)) (* 30.0 (sin sweep)))
          mid (list (* 30.0 (cos (/ sweep 2.0))) (* 30.0 (sin (/ sweep 2.0))))
          arc (list '(kind . arc) '(center 0.0 0.0) '(radius . 30.0) '(start-angle . 0.0) (cons 'sweep sweep))
          paths (list (ast:n-test-path 0 (list arc) settings)) connections nil id 1)
    (foreach primitive (list
      (ast:n-test-line start '(40.5 0.0))
      (ast:n-test-line start '(30.0 -10.5))
      (ast:n-test-line end (ast:g-add end (list (* 10.5 (cos sweep)) (* 10.5 (sin sweep)))))
      (ast:n-test-line end (ast:g-add end (list (* -10.5 (sin sweep)) (* 10.5 (cos sweep))))))
      (setq arm (ast:n-test-path id (list primitive) settings)
            connections (append connections (ast:n-test-remap (ast:n-test-connections (car paths) arm) 1 id))
            paths (append paths (list arm)) id (1+ id)))
    (setq result (ast:g-solve-set paths connections)
          slits (vl-remove-if-not '(lambda (opening) (and (= 'slit (ast:g-get 'type opening nil))
            (equal mid (ast:g-get 'center opening nil) 1e-8))) (ast:g-get 'openings result nil)))
    (setq tangent-hits (ast:n-test-connections (car paths) (last paths)))
    (ast:n-test (and (= 1 (length tangent-hits)) (equal end (ast:g-get 'point (car tangent-hits) nil) 1e-8)
      (= 1 (length (ast:n-test-connections (last paths) (car paths)))))
      "An exact tangent arc endpoint remains one finite connection in either guide order")
    (setq primitive (car (ast:g-get 'primitives (ast:g-get 'route (last paths) nil) nil))
          arm (ast:n-test-path 5 (list (ast:n-test-shift-primitive primitive
      (list (* 1e-6 (cos sweep)) (* 1e-6 (sin sweep))))) settings))
    (ast:n-test (and (null (ast:n-test-connections (car paths) arm)) (null (ast:n-test-connections arm (car paths))))
      "A tangent guide outside the endpoint tolerance does not acquire a connection")
    (if old-chord
      (ast:n-test (and (not (ast:g-get 'ok result nil)) (null (ast:g-get 'openings result nil))
        (wcmatch (ast:g-get 'error result "") "Connected line: Stitches cannot fit this section*"))
        "A pitch-long chord between curved branch holes cannot replace two half-pitch chords")
      (ast:n-test (and (ast:g-get 'ok result nil) (= 2 (length (ast:n-test-rounds result))) (= 1 (length slits))
        (vl-every '(lambda (gap) (or (/= 'junction (ast:g-get 'kind gap nil)) (equal 1.5 (ast:g-get 'distance gap 0.0) 1e-8)))
          (ast:g-get 'intervals result nil)))
        "Two curved branch reservations share one midpoint slit at exact half-pitch chords"))))
(defun ast:n-test-stitch-hand (settings / reverse-settings first second paths connections result)
  (setq reverse-settings (ast:n-put 'stitch-hand -1 settings))
  (ast:n-test-half-pitch reverse-settings)
  (ast:n-test-curved-link reverse-settings)
  (setq first (ast:n-test-path 0 (list (ast:n-test-line '(-10.5 0.0) '(10.5 0.0))) reverse-settings)
        second (ast:n-test-path 1 (list (ast:n-test-line '(0.0 0.0) '(0.0 10.5))) reverse-settings)
        paths (list first second) connections (ast:n-test-connections first second)
        result (ast:g-solve-set paths connections))
  (ast:n-test (and (ast:g-get 'ok result nil)
    (vl-every '(lambda (gap) (or (/= 'junction (ast:g-get 'kind gap nil))
      (equal 1.5 (ast:g-get 'distance gap nil) 1e-8))) (ast:g-get 'intervals result nil)))
    "Reverse stitch T junctions retain fixed half-pitch neighbours")
  (setq second (ast:n-put 'settings settings second)
        result (ast:g-solve-set (list first second) connections))
  (ast:n-test (and (not (ast:g-get 'ok result nil)) (null (ast:g-get 'openings result nil)))
    "Connected guides with different stitch leans reject before creating partial output"))

(defun ast:n-tests (/ ast:n-test-count ast:n-test-failures settings horizontal vertical aa bb cc paths connections result reference circle arc closed shifted resolved selected modified openings opening rounds edge ordinary node hole near-count connection-a connection-b gap-result)
  (setq ast:n-test-count 0 ast:n-test-failures nil settings '((pitch . 3.0) (thickness . 0.2) (margin . 0.2)))
  (setq horizontal (ast:n-test-path 0 (list (ast:n-test-line '(-10.5 0.0) '(10.5 0.0))) settings)
        vertical (ast:n-test-path 1 (list (ast:n-test-line '(0.0 0.0) '(0.0 10.5))) settings)
        connections (ast:n-test-connections horizontal vertical) paths (list horizontal vertical)
        result (ast:g-solve-set paths connections))
  (ast:n-test (and (= (length connections) 1) (= (length (ast:g-get 'incidences (car connections) nil)) 2)) "T finite intersection has two source incidences")
  (ast:n-test (and (ast:g-get 'ok result nil) (= (length (ast:g-get 'openings result nil)) 13) (= (length (ast:n-test-rounds result)) 1)) "T emits one shared hole and twelve ordinary slits")
  (ast:n-test (not (ast:g-get 'ok (ast:g-solve-set paths nil) nil)) "undeclared crossing requires Connect")
  (setq vertical (ast:n-test-path 1 (list (ast:n-test-line '(0.0 -10.5) '(0.0 10.5))) settings)
        connections (ast:n-test-connections horizontal vertical) result (ast:g-solve-set (list horizontal vertical) connections))
  (ast:n-test (and (ast:g-get 'ok result nil) (= (length (ast:g-get 'openings result nil)) 17) (= (length (ast:n-test-rounds result)) 1)) "X emits one shared hole and sixteen ordinary slits")
  (setq aa (ast:n-test-path 0 (list (ast:n-test-line '(-30.0 0.0) '(0.0 0.0))) settings)
        bb (ast:n-test-path 1 (list (ast:n-test-line '(0.0 0.0) '(0.0 -30.0))) settings)
        connections (ast:n-test-connections aa bb) result (ast:g-solve-set (list aa bb) connections)
        reference (ast:g-solve (list (cons 'primitives (append (ast:g-get 'primitives (ast:g-get 'route aa nil) nil) (ast:g-get 'primitives (ast:g-get 'route bb nil) nil)))) settings nil))
  (ast:n-test (ast:n-test-same-cuts result reference) "separate endpoint LINEs equal ordered polyline corner")
  (setq aa (ast:n-test-path 0 (list (ast:n-test-line '(-38.0 258.0) '(107.80342046542515 215.04231639645309))) settings)
        bb (ast:n-test-path 1 (list (ast:n-test-line '(107.80342046542515 215.04231639645309) '(285.06457440910435 231.24365283994626))) settings)
        connections (ast:n-test-connections aa bb) result (ast:g-solve-set (list aa bb) connections)
        reference (ast:g-solve (list (cons 'primitives (append (ast:g-get 'primitives (ast:g-get 'route aa nil) nil)
          (ast:g-get 'primitives (ast:g-get 'route bb nil) nil)))) settings nil))
  (ast:n-test (and (ast:n-test-same-cuts result reference)
    (= 1 (length (ast:g-get 'corner-adjustments result nil))) (= 'adjusted (ast:g-get 'status result nil)))
    "Connected shallow guides use the same adjusted corner and physical openings as one polyline")
  (setq result (ast:g-solve-set (list bb aa) connections))
  (ast:n-test (and (ast:n-test-same-cuts result reference)
    (= 1 (length (ast:g-get 'corner-adjustments result nil))))
    "Reversing guide selection order preserves the shallow corner and its adjusted slit")
  (setq bb (ast:n-put 'settings (ast:n-put 'corrections nil settings) bb))
  (ast:n-test (not (ast:g-get 'ok (ast:g-solve-set (list aa bb) connections) nil))
    "Connected corner respects the outgoing guide's disabled adjustment setting")
  (setq aa (ast:n-test-path 0 (list (ast:n-test-line '(-30.0 0.0) '(0.0 0.0))) settings)
        bb (ast:n-test-path 1 (list (ast:n-test-line '(0.0 0.0) '(0.0 -30.0))) settings)
        connections (ast:n-test-connections aa bb))
  (setq bb (ast:n-put 'settings (ast:n-put 'pitch 4.0 settings) bb)
        result (ast:g-solve-set (list aa bb) connections))
  (ast:n-test (and (ast:g-get 'ok result nil) (= (length (ast:n-test-rounds result)) 1)) "two-arm corner respects separate incoming and outgoing pitch")
  (setq aa (ast:n-test-path 0 (list (ast:n-test-line '(0.0 0.0) '(11.0 0.0))) settings)
        bb (ast:n-test-path 1 (list (ast:n-test-line '(11.0 0.0) '(30.0 0.0))) settings)
        result (ast:g-solve-set (list aa bb) (ast:n-test-connections aa bb))
        reference (ast:g-solve (list (cons 'primitives (list (ast:n-test-line '(0.0 0.0) '(30.0 0.0))))) settings nil))
  (ast:n-test (ast:n-test-same-cuts result reference) "independent collinear subdivisions do not impose false phase")
  (setq aa (ast:n-test-path 0 (list (ast:n-test-line '(0.0 0.0) '(30.0 0.0))) settings)
        bb (ast:n-test-path 1 (list (ast:n-test-line '(10.0 0.0) '(40.0 0.0))) settings))
  (ast:n-test (not (ast:g-get 'ok (ast:g-connect-candidates (ast:g-get 'route aa nil) (ast:g-get 'route bb nil)) nil)) "positive-length overlap is rejected")
  (setq aa horizontal bb (ast:n-test-path 1 (list (ast:n-test-line '(0.0 0.0) '(0.0 10.5))) (ast:n-put 'pitch 4.0 settings))
        result (ast:g-solve-set (list aa bb) (ast:n-test-connections aa bb)))
  (ast:n-test (and (ast:g-get 'ok result nil) (= (length (ast:g-get 'openings result nil)) 12)
    (vl-some '(lambda (opening) (equal '(0.0 2.0) (ast:g-get 'center opening nil) 1e-8)) (ast:g-get 'openings result nil))
    (vl-every '(lambda (point) (vl-some '(lambda (opening) (equal point (ast:g-get 'center opening nil) 1e-8))
      (ast:g-get 'openings result nil))) '((-1.5 0.0) (1.5 0.0)))) "branch arms may retain different nominal pitches")
  (setq bb (ast:n-put 'settings (ast:n-put 'diameter 0.7 settings) bb))
  (ast:n-test (not (ast:g-get 'ok (ast:g-solve-set (list aa bb) (ast:n-test-connections aa bb)) nil)) "incompatible physical hole profiles reject")
  (setq aa horizontal bb (ast:n-test-path 1 (list (ast:n-test-line '(0.0 0.0) '(0.0 10.5))) settings)
        aa (ast:n-put 'landmarks '(((primitive . 0) (station . 10.5))) aa))
  (ast:n-test (not (ast:g-get 'ok (ast:g-solve-set (list aa bb) (ast:n-test-connections aa bb)) nil)) "shared-hole versus centred-gap conflict rejects")
  (setq aa (ast:n-put 'settings (ast:n-put 'start 13.0 settings) horizontal))
  (ast:n-test (not (ast:g-get 'ok (ast:g-solve-set (list aa bb) (ast:n-test-connections aa bb)) nil)) "range cannot silently discard connected intersection")
  (setq aa (ast:n-put 'settings (ast:n-put 'reverse T settings) horizontal)
        result (ast:g-solve-set (list aa bb) (ast:n-test-connections aa bb)))
  (ast:n-test (and (ast:g-get 'ok result nil) (= (length (ast:g-get 'openings result nil)) 13)) "reverse range retains source intersection attachment")
  ;; Two branch holes reserve half-pitch neighbours; a p-long link shares its middle slit.
  (foreach edge '(3.0 6.0 7.0)
    (setq aa (ast:n-test-path 0 (list (ast:n-test-line '(-10.5 0.0) (list (+ edge 10.5) 0.0))) settings)
          bb (ast:n-test-path 1 (list (ast:n-test-line '(0.0 0.0) '(0.0 10.5))) settings)
          cc (ast:n-test-path 2 (list (ast:n-test-line (list edge 0.0) (list edge -10.5))) settings)
          connection-a (ast:n-test-connections aa bb)
          connection-b (ast:n-test-remap (ast:n-test-connections aa cc) 1 2)
          result (ast:g-solve-set (list aa bb cc) (append connection-a connection-b)))
    (ast:n-test (if (= edge 7.0) (not (ast:g-get 'ok result nil))
      (and (ast:g-get 'ok result nil) (= (length (ast:n-test-rounds result)) 2) (= (length (ast:g-get 'openings result nil)) (if (= edge 3.0) 19 20))
        (vl-every '(lambda (gap) (or (/= 'junction (ast:g-get 'kind gap nil)) (equal 1.5 (ast:g-get 'distance gap 0.0) 1e-8)))
          (ast:g-get 'intervals result nil))
        (vl-some '(lambda (opening) (and (= 'slit (ast:g-get 'type opening nil)) (equal '(1.5 0.0) (ast:g-get 'center opening nil) 1e-8)))
          (ast:g-get 'openings result nil))))
      (strcat "two branch nodes with " (rtos edge 2 0) " mm edge")))
  ;; A connected circle derives phase from its physical nodes, not its CAD seam.
  (setq circle (list '(kind . arc) '(center 0.0 0.0) '(radius . 10.0) '(start-angle . 0.0) (cons 'sweep (* 2.0 pi)))
        aa (ast:n-test-path 0 (list circle) settings)
        aa (ast:n-put 'route (ast:n-put 'closed T (ast:g-get 'route aa nil)) aa)
        bb (ast:n-test-path 1 (list (ast:n-test-line '(0.0 10.0) '(0.0 20.5))) settings)
        connections (ast:n-test-connections aa bb) result (ast:g-solve-set (list aa bb) connections))
  (ast:n-test (and (ast:g-get 'ok result nil) (= (length (ast:n-test-rounds result)) 1)) "circle endpoint-line T supports curved arms")
  (setq reference result aa (ast:n-put 'settings (ast:n-put 'phase 7.0 settings) aa)
        result (ast:g-solve-set (list aa bb) connections))
  (ast:n-test (ast:n-test-same-cuts result reference) "circle phase does not introduce a second physical anchor")
  (setq hole '(0.0 10.0) near-count 0)
  (foreach opening (ast:g-get 'openings result nil)
    (if (and (= (ast:g-get 'type opening nil) 'slit) (ast:g-near (ast:g-dist hole (ast:g-get 'center opening nil)) 1.5)) (setq near-count (1+ near-count))))
  (ast:n-test (= near-count 3) "curved branch first gaps are exact half-pitch chords")
  ;; Two finite roots require explicit selection and preserve their branch on edits.
  (setq aa (ast:n-test-path 0 (list (ast:n-test-line '(-14.5 0.0) '(14.5 0.0))) settings)
        bb (ast:n-test-path 1 (list circle) settings)
        bb (ast:n-put 'route (ast:n-put 'closed T (ast:g-get 'route bb nil)) bb)
        connections (ast:n-test-connections aa bb))
  (ast:n-test (= (length connections) 2) "line circle enumerates both finite intersections")
  (setq selected (list (car connections)) shifted (list (ast:n-test-shift-path aa '(100.0 70.0)) (ast:n-test-shift-path bb '(100.0 70.0)))
        resolved (ast:g-resolve-connections shifted selected))
  (ast:n-test (and (ast:g-get 'ok resolved nil) (< (ast:g-dist (ast:g-get 'point (car (ast:g-get 'connections resolved nil)) nil)
    (ast:g-add (ast:g-get 'point (car selected) nil) '(100.0 70.0))) 1e-8)) "saved intersection follows provable common move")
  (setq modified (ast:n-put 'route (list (cons 'primitives (list (ast:n-put 'radius 11.0 circle))) '(closed . T)) bb)
        resolved (ast:g-resolve-connections (list aa modified) selected))
  (ast:n-test (and (ast:g-get 'ok resolved nil) (= (ast:g-sign (car (ast:g-get 'point (car (ast:g-get 'connections resolved nil)) nil)))
    (ast:g-sign (car (ast:g-get 'point (car selected) nil))))) "radius edit retains selected analytic root side")
  (ast:n-test (not (ast:g-get 'ok (ast:g-solve-set (list aa bb) selected) nil)) "second undeclared circle crossing is not silently coordinated")
  (setq result (ast:g-solve-set (list aa bb) connections))
  (ast:n-test (and (ast:g-get 'ok result nil) (= (length (ast:n-test-rounds result)) 2)) "two declared circle intersections share two holes")
  ;; Changed topology must not attach the saved primitive index to a different segment.
  (setq modified (ast:n-put 'route (list (cons 'primitives (list (ast:n-test-line '(-14.5 0.0) '(0.0 0.0)) (ast:n-test-line '(0.0 0.0) '(14.5 0.0))))) aa))
  (ast:n-test (not (ast:g-get 'ok (ast:g-resolve-connections (list modified bb) selected) nil)) "topology changes request an explicit repick")
  (setq modified (ast:n-put 'route (list (cons 'primitives (list (ast:g-reverse-primitive (car (ast:g-get 'primitives (ast:g-get 'route aa nil) nil)))))) aa)
        resolved (ast:g-resolve-connections (list modified bb) selected))
  (ast:n-test (and (ast:g-get 'ok resolved nil) (< (ast:g-dist (ast:g-get 'point (car (ast:g-get 'connections resolved nil)) nil)
    (ast:g-get 'point (car selected) nil)) 1e-8)) "native line reversal retains same physical chosen root")
  ;; A common move can put the unselected root at the former selected point.
  (setq shifted (list (ast:n-test-shift-path aa '(20.0 0.0)) (ast:n-test-shift-path bb '(20.0 0.0)))
        resolved (ast:g-resolve-connections shifted connections))
  (ast:n-test (and (ast:g-get 'ok resolved nil) (= (length (ast:g-get 'connections resolved nil)) 2)
    (< (ast:g-dist (ast:g-get 'point (car (ast:g-get 'connections resolved nil)) nil)
      (ast:g-add (ast:g-get 'point (car connections) nil) '(20.0 0.0))) 1e-8)) "common motion wins over an old-world-point coincidence")
  ;; Several declarations at one physical point form one opening, transitively.
  (setq aa (ast:n-test-path 0 (list (ast:n-test-line '(-10.5 0.0) '(0.0 0.0))) settings)
        bb (ast:n-test-path 1 (list (ast:n-test-line '(0.0 0.0) '(0.0 10.5))) settings)
        cc (ast:n-test-path 2 (list (ast:n-test-line '(0.0 0.0) '(10.5 0.0))) settings)
        connections (append (ast:n-test-connections aa bb) (ast:n-test-remap (ast:n-test-connections aa cc) 1 2))
        reference (ast:g-solve-set (list aa bb cc) connections)
        result (ast:g-solve-set (list cc bb aa) connections))
  (ast:n-test (and (ast:g-get 'ok reference nil) (= (length (ast:g-get 'openings reference nil)) 13) (= (length (ast:n-test-rounds reference)) 1)) "three co-located declarations reuse one physical hole")
  (ast:n-test (ast:n-test-same-cuts result reference) "member enumeration order does not change T geometry")
  (setq aa (ast:n-test-path 0 (list (ast:n-test-line '(-10.5 0.0) '(0.0 0.0)) (ast:n-test-line '(0.0 0.0) '(0.0 10.5))) settings)
        bb (ast:n-test-path 1 (list (ast:n-test-line '(0.0 0.0) '(10.5 0.0))) settings)
        result (ast:g-solve-set (list aa bb) (ast:n-test-connections aa bb)))
  (ast:n-test (ast:n-test-same-cuts result reference) "polyline corner plus third branch equals three separate arms")
  ;; Curved branch cases exercise all-arc finite intersections and tangent-aligned cuts.
  (setq aa (ast:n-test-path 0 (list circle) settings)
        aa (ast:n-put 'route (ast:n-put 'closed T (ast:g-get 'route aa nil)) aa)
        arc (list '(kind . arc) '(center 10.0 10.0) '(radius . 10.0) (cons 'start-angle (- (/ pi 2.0))) (cons 'sweep (+ (* 2.0 (ast:g-asin 0.075)) (* 6.0 (ast:g-asin 0.15)))))
        bb (ast:n-test-path 1 (list arc) settings)
        connections (ast:n-test-connections aa bb) result (ast:g-solve-set (list aa bb) connections))
  (ast:n-test (and (= (length connections) 1) (ast:g-get 'ok result nil) (= (length (ast:n-test-rounds result)) 1)) "arc endpoint to circle interior T")
  (setq aa (ast:n-test-path 0 (list (ast:n-put 'center '(-5.0 0.0) circle)) settings)
        aa (ast:n-put 'route (ast:n-put 'closed T (ast:g-get 'route aa nil)) aa)
        bb (ast:n-test-path 1 (list (ast:n-put 'center '(5.0 0.0) circle)) settings)
        bb (ast:n-put 'route (ast:n-put 'closed T (ast:g-get 'route bb nil)) bb)
        connections (ast:n-test-connections aa bb) result (ast:g-solve-set (list aa bb) connections))
  (ast:n-test (and (= (length connections) 2) (ast:g-get 'ok result nil) (= (length (ast:n-test-rounds result)) 2)) "two circle-circle X nodes")
  (setq selected (list (car connections))
        modified (ast:n-put 'route (list (cons 'primitives (mapcar 'ast:g-reverse-primitive (ast:g-get 'primitives (ast:g-get 'route aa nil) nil))) '(closed . T)) aa)
        resolved (ast:g-resolve-connections (list modified bb) selected))
  (ast:n-test (and (ast:g-get 'ok resolved nil) (< (ast:g-dist (ast:g-get 'point (car (ast:g-get 'connections resolved nil)) nil)
    (ast:g-get 'point (car selected) nil)) 1e-8)) "one full-circle traversal reversal preserves physical root")
  (setq shifted (ast:n-put 'route (list (cons 'primitives (mapcar 'ast:g-reverse-primitive (ast:g-get 'primitives (ast:g-get 'route bb nil) nil))) '(closed . T)) bb)
        resolved (ast:g-resolve-connections (list modified shifted) selected))
  (ast:n-test (and (not (ast:g-get 'ok resolved nil)) (= (type (ast:g-get 'error resolved nil)) 'STR)
    (wcmatch (ast:g-get 'error resolved "") "*more than one possible match*")) "symmetric circle reversal cannot silently become a reflected root")
  (setq resolved (ast:g-resolve-connections (list (ast:n-test-shift-path modified '(20.0 30.0)) (ast:n-test-shift-path shifted '(20.0 30.0))) selected))
  (ast:n-test (not (ast:g-get 'ok resolved nil)) "translated symmetric reversal still requires explicit attachment repair")
  ;; A source direction edit must not invert root identity during another edit.
  (setq aa (ast:n-test-path 0 (list (ast:n-test-line '(-14.5 0.0) '(14.5 0.0))) settings)
        bb (ast:n-test-path 1 (list circle) settings)
        bb (ast:n-put 'route (ast:n-put 'closed T (ast:g-get 'route bb nil)) bb)
        connections (ast:n-test-connections aa bb)
        modified (ast:n-put 'route (list (cons 'primitives (list (ast:n-test-line '(14.5 0.0) '(-14.5 0.0))))) aa)
        shifted (ast:n-put 'route (list (cons 'primitives (list (ast:n-put 'radius 11.0 circle))) '(closed . T)) bb))
  (foreach node connections
    (setq resolved (ast:g-resolve-connections (list modified shifted) (list node)))
    (ast:n-test (and (ast:g-get 'ok resolved nil)
      (< (ast:g-dist (ast:g-get 'point (car (ast:g-get 'connections resolved nil)) nil)
        (list (* 11.0 (ast:g-sign (car (ast:g-get 'point node nil)))) 0.0)) 1e-8))
      "line reversal plus radius edit preserves selected positive or negative root"))
  ;; AutoLISP OR returns a boolean, so error messages must be propagated explicitly.
  (setq result (ast:g-connect-candidates nil (ast:g-get 'route aa nil)))
  (ast:n-test (and (not (ast:g-get 'ok result nil)) (= (type (ast:g-get 'error result nil)) 'STR)
    (= (ast:g-get 'error result nil) "No usable stitch line was found. Select a line or curve.")) "first invalid candidate route preserves diagnostic string")
  (setq result (ast:g-connect-candidates (ast:g-get 'route aa nil) nil))
  (ast:n-test (and (not (ast:g-get 'ok result nil)) (= (type (ast:g-get 'error result nil)) 'STR)) "second invalid candidate route preserves diagnostic string")
  (setq result (ast:n-prepare (ast:n-put 'settings '((pitch . -1.0)) aa)))
  (ast:n-test (and (not (ast:g-get 'ok result nil)) (= (type (ast:g-get 'error result nil)) 'STR)) "invalid physical profile preserves diagnostic string")
  (setq result (ast:n-prepare (ast:n-put 'route nil aa)))
  (ast:n-test (and (not (ast:g-get 'ok result nil)) (= (type (ast:g-get 'error result nil)) 'STR)) "invalid prepared route preserves diagnostic string")
  ;; Swapping circle/line incidence order must not change the selected-root rule.
  (setq reference aa aa (ast:n-put 'id 0 bb) bb (ast:n-put 'id 1 reference)
        connections (ast:n-test-connections aa bb)
        modified (ast:n-put 'route (list (cons 'primitives (list (ast:n-put 'radius 11.0 circle))) '(closed . T)) aa)
        shifted (ast:n-put 'route (list (cons 'primitives (list (ast:n-test-line '(14.5 0.0) '(-14.5 0.0))))) bb))
  (foreach node connections
    (setq resolved (ast:g-resolve-connections (list modified shifted) (list node)))
    (ast:n-test (and (ast:g-get 'ok resolved nil)
      (< (ast:g-dist (ast:g-get 'point (car (ast:g-get 'connections resolved nil)) nil)
        (list (* 11.0 (ast:g-sign (car (ast:g-get 'point node nil)))) 0.0)) 1e-8))
      "circle-first incidence order preserves reversed-line edited-radius root"))
  (ast:n-test-shallow-junctions settings)
  (ast:n-test-half-pitch settings)
  (ast:n-test-stitch-hand settings)
  (ast:n-test-curved-link settings)
  (list (cons 'ok (null ast:n-test-failures)) (cons 'count ast:n-test-count) (cons 'failures (reverse ast:n-test-failures))))
(princ)
