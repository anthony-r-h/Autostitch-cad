;;; Load AUTOSTITCH.lsp first; run (ast:create-demo) in an empty disposable drawing.
(defun ast:demo-fail (message)
  (setq ast:*cad-error* message)
  (princ (strcat "\nAutostitch demo: " message))
  (exit))
(defun ast:demo-label (point caption)
  (entmakex (list '(0 . "TEXT") '(8 . "DEMO-NOTES") (cons 10 point)
    '(40 . 1.8) (cons 1 caption))))
(defun ast:demo-generate (guide gaps / result)
  (setq result (ast:cad-generate guide (ast:cad-default-settings) gaps))
  (if (not (ast:cad-get 'ok result))
    (ast:demo-fail (strcat "Generation failed: " (ast:cad-get 'error result))))
  (setq ast:demo:*guides* (append ast:demo:*guides* (list guide)))
  result)
(defun ast:demo-connect (first second caption / result)
  (setq result (ast:cad-connect first second nil (ast:cad-default-settings) nil))
  (if (not (ast:cad-get 'ok result))
    (ast:demo-fail (strcat caption " could not connect: " (ast:cad-get 'error result))))
  (setq ast:demo:*guides* (append ast:demo:*guides* (list first second)))
  result)
(defun ast:demo-corner-generate (guide / state settings primitives incoming outgoing corner before after step-in step-out start finish result)
  ;; Choose free outer margins that fit the corner's nominal stitch phase.
  (setq state (ast:cad-read guide) settings (ast:cad-default-settings)
        primitives (ast:cad-get 'primitives (ast:cad-get 'route state))
        incoming (car primitives) outgoing (cadr primitives)
        corner (ast:g-corner incoming outgoing settings))
  (if (not (ast:cad-get 'ok corner)) (ast:demo-fail (ast:cad-get 'error corner)))
  (setq before (ast:cad-get 'incoming-station corner) after (ast:cad-get 'outgoing-station corner)
        step-in (ast:g-step incoming 3.0) step-out (ast:g-step outgoing 3.0)
        start (- before (* step-in (ast:g-floor-near (/ before step-in))))
        finish (+ after (* step-out (ast:g-floor-near (/ (- (ast:g-length outgoing) after) step-out))))
        settings (ast:cad-put 'start start settings)
        settings (ast:cad-put 'end (+ (ast:g-length incoming) finish) settings)
        settings (ast:cad-put 'start-anchor
          (ast:cad-range-anchor guide (list '(primitive . 0) (cons 'station start))) settings)
        settings (ast:cad-put 'end-anchor
          (ast:cad-range-anchor guide (list '(primitive . 1) (cons 'station finish))) settings)
        result (ast:cad-generate guide settings nil))
  (if (not (ast:cad-get 'ok result)) (ast:demo-fail (ast:cad-get 'error result)))
  (setq ast:demo:*guides* (append ast:demo:*guides* (list guide)))
  result)
(defun ast:demo-curved-corner (origin second-kind turn / sweep bulge first last center guide)
  (setq sweep (/ pi 3.0) bulge (- (/ (sin (/ sweep 4.0)) (cos (/ sweep 4.0))))
        first (mapcar '+ origin (list (- (* 10.0 (sin sweep))) (- (* 10.0 (cos sweep)) 10.0))))
  (if (= second-kind 'line)
    (setq last (mapcar '+ origin (list (* 10.0 (cos turn)) (- (* 10.0 (sin turn))))))
    (setq center (mapcar '+ origin (list (- (* 8.0 (sin turn))) (- (* 8.0 (cos turn)))))
          last (mapcar '+ center (list (* 8.0 (cos (- (/ pi 2.0) turn sweep)))
                                      (* 8.0 (sin (- (/ pi 2.0) turn sweep)))))))
  (setq guide (entmakex (list '(0 . "LWPOLYLINE") '(100 . "AcDbEntity") '(8 . "DEMO-GUIDES")
    '(100 . "AcDbPolyline") '(90 . 3) '(70 . 0) (cons 10 first) (cons 42 bulge)
    (cons 10 origin) (cons 42 (if (= second-kind 'arc) bulge 0.0)) (cons 10 last))))
  (ast:demo-corner-generate guide))
(defun ast:create-demo (/ document guide first second layer data)
  (ast:load-components)
  (setq document (vla-get-ActiveDocument (vlax-get-acad-object)))
  (if (> (vla-get-Count (vla-get-ModelSpace document)) 0)
    (ast:demo-fail "Create the demo in an empty drawing."))
  (setvar "INSUNITS" 4) (setvar "TILEMODE" 1)
  (foreach layer '(("DEMO-GUIDES" . 8) ("DEMO-NOTES" . 8) ("AUTOSTITCH" . 7) ("AUTOSTITCH_UI" . 7))
    (if (not (tblsearch "LAYER" (car layer)))
      (if (not (entmake (list '(0 . "LAYER") '(100 . "AcDbSymbolTableRecord")
        '(100 . "AcDbLayerTableRecord") (cons 2 (car layer)) '(70 . 0)
        (cons 62 (cdr layer)) '(6 . "Continuous"))))
        (ast:demo-fail (strcat "Could not create layer " (car layer)))))
    (setq data (ast:cad-put 62 (cdr layer) (entget (tblobjname "LAYER" (car layer)))))
    (if (= (car layer) "AUTOSTITCH_UI") (setq data (ast:cad-put 290 0 data)))
    (if (not (entmod data)) (ast:demo-fail (strcat "Could not set up layer " (car layer)))))
  (setq ast:demo:*guides* nil)
  (ast:demo-label '(0.0 90.0 0.0) "AUTOSTITCH  |  Select stitch line, change pitch, Generate stitches")
  (ast:demo-label '(0.0 84.0 0.0) "Connect stitch lines where they meet or cross. Edit a source, then Generate stitches.")
  (ast:demo-label '(0.0 78.0 0.0) "I marks: adjusted spacing. S / E: start / end. J: junction. L#: landmark.")
  (ast:demo-label '(0.0 68.0 0.0) "Straight line / pattern landmark at 31.5 mm")
  (setq guide (entmakex '((0 . "LINE") (8 . "DEMO-GUIDES") (10 0.0 63.0 0.0) (11 70.5 63.0 0.0))))
  (entmakex '((0 . "LINE") (8 . "DEMO-GUIDES") (10 31.5 55.0 0.0) (11 31.5 66.0 0.0)))
  (ast:demo-generate guide '(((primitive . 0) (station . 31.5))))
  (ast:demo-label '(0.0 40.0 0.0) "Closed line / four corners")
  (setq guide (entmakex '((0 . "LWPOLYLINE") (100 . "AcDbEntity") (8 . "DEMO-GUIDES")
    (100 . "AcDbPolyline") (90 . 4) (70 . 1) (10 0.0 0.0) (10 60.0 0.0) (10 60.0 30.0) (10 0.0 30.0))))
  (ast:demo-generate guide nil)
  (ast:demo-label '(0.0 -12.0 0.0) "Line / tangent arc / line")
  (setq guide (entmakex '((0 . "LWPOLYLINE") (100 . "AcDbEntity") (8 . "DEMO-GUIDES")
    (100 . "AcDbPolyline") (90 . 4) (70 . 0) (10 0.0 -45.0) (42 . 0.0)
    (10 30.0 -45.0) (42 . 0.4142135623730950) (10 45.0 -30.0) (42 . 0.0) (10 45.0 -18.0) (42 . 0.0))))
  (ast:demo-generate guide nil)
  (ast:demo-label '(84.0 40.0 0.0) "Closed circle")
  (setq guide (entmakex '((0 . "CIRCLE") (8 . "DEMO-GUIDES") (10 105.0 15.0 0.0) (40 . 20.0))))
  (ast:demo-generate guide nil)
  (ast:demo-label '(160.0 68.0 0.0) "Connected T")
  (ast:demo-label '(160.0 63.0 0.0) "Two lines / one shared hole")
  (setq first (entmakex '((0 . "LINE") (8 . "DEMO-GUIDES") (10 164.0 45.0 0.0) (11 188.0 45.0 0.0)))
        second (entmakex '((0 . "LINE") (8 . "DEMO-GUIDES") (10 176.0 45.0 0.0) (11 176.0 57.0 0.0))))
  (ast:demo-connect first second "Connected T")
  (ast:demo-label '(225.0 68.0 0.0) "Connected X")
  (ast:demo-label '(225.0 63.0 0.0) "Two lines / one shared hole")
  (setq first (entmakex '((0 . "LINE") (8 . "DEMO-GUIDES") (10 230.0 45.0 0.0) (11 254.0 45.0 0.0)))
        second (entmakex '((0 . "LINE") (8 . "DEMO-GUIDES") (10 242.0 33.0 0.0) (11 242.0 57.0 0.0))))
  (ast:demo-connect first second "Connected X")
  (ast:demo-label '(160.0 25.0 0.0) "90-degree corner")
  (ast:demo-label '(160.0 20.0 0.0) "Two separate lines / no Join")
  (setq first (entmakex '((0 . "LINE") (8 . "DEMO-GUIDES") (10 160.0 0.0 0.0) (11 190.0 0.0 0.0)))
        second (entmakex '((0 . "LINE") (8 . "DEMO-GUIDES") (10 190.0 0.0 0.0) (11 190.0 -30.0 0.0))))
  (ast:demo-connect first second "Separate-line corner")
  (ast:demo-label '(220.0 25.0 0.0) "Circle + line / two crossings")
  (ast:demo-label '(220.0 20.0 0.0) "ConnectAll / two shared holes")
  (setq first (entmakex '((0 . "LINE") (8 . "DEMO-GUIDES") (10 226.0 -8.0 0.0) (11 258.0 -8.0 0.0)))
        second (entmakex '((0 . "CIRCLE") (8 . "DEMO-GUIDES") (10 242.0 -8.0 0.0) (40 . 10.0))))
  (ast:demo-connect first second "Circle and line")
  (ast:demo-label '(0.0 -65.0 0.0) "JUNCTION EXAMPLES  |  3 mm pitch, same physical scale as the examples above")
  (ast:demo-label '(0.0 -71.0 0.0) "J03 / J04 / A03 / A04 retain the HTML guides; outer margins follow the native corner phase.")
  (ast:demo-label '(0.0 -84.0 0.0) "J03: straight / 135-degree inside angle")
  (ast:demo-label '(0.0 -89.0 0.0) "45-degree tangent turn")
  (setq guide (entmakex '((0 . "LWPOLYLINE") (100 . "AcDbEntity") (8 . "DEMO-GUIDES")
    (100 . "AcDbPolyline") (90 . 3) (70 . 0)
    (10 2.0 -110.0) (10 12.0 -110.0) (10 19.0710678118655 -117.0710678118655))))
  (ast:demo-corner-generate guide)
  (ast:demo-label '(80.0 -84.0 0.0) "J04: straight / 45-degree inside angle")
  (ast:demo-label '(80.0 -89.0 0.0) "135-degree tangent turn")
  (setq guide (entmakex '((0 . "LWPOLYLINE") (100 . "AcDbEntity") (8 . "DEMO-GUIDES")
    (100 . "AcDbPolyline") (90 . 3) (70 . 0)
    (10 82.0 -110.0) (10 92.0 -110.0) (10 84.9289321881345 -117.0710678118655))))
  (ast:demo-corner-generate guide)
  (ast:demo-label '(160.0 -84.0 0.0) "A03: arc to line / R10")
  (ast:demo-label '(160.0 -89.0 0.0) "90-degree tangent turn")
  (ast:demo-curved-corner '(172.0 -110.0) 'line (/ pi 2.0))
  (ast:demo-label '(0.0 -140.0 0.0) "A04: arc to arc / R10 and R8")
  (ast:demo-label '(0.0 -145.0 0.0) "90-degree tangent turn")
  (ast:demo-curved-corner '(12.0 -165.0) 'arc (/ pi 2.0))
  (ast:demo-label '(80.0 -140.0 0.0) "Arc to line / R10")
  (ast:demo-label '(80.0 -145.0 0.0) "60-degree tangent turn")
  (ast:demo-curved-corner '(92.0 -165.0) 'line (/ pi 3.0))
  (ast:demo-label '(160.0 -140.0 0.0) "Polyline + line / one connected stitch layout")
  (ast:demo-label '(160.0 -145.0 0.0) "45-degree polyline corner; 120-degree joining turn")
  (setq first (entmakex '((0 . "LWPOLYLINE") (100 . "AcDbEntity") (8 . "DEMO-GUIDES")
          (100 . "AcDbPolyline") (90 . 3) (70 . 0)
          (10 160.0 -165.0) (10 180.0 -165.0) (10 195.0 -150.0)))
        second (entmakex (list '(0 . "LINE") '(8 . "DEMO-GUIDES") '(10 195.0 -150.0 0.0)
          (list 11 (+ 195.0 (* 25.0 (cos (* pi (/ 75.0 180.0)))))
                   (- -150.0 (* 25.0 (sin (* pi (/ 75.0 180.0))))) 0.0))))
  (ast:demo-connect first second "Polyline and line")
  (ast:demo-label '(0.0 -190.0 0.0) "3 mm pitch. Physical tool width and margin still need calibration.")
  (vla-ZoomExtents (vlax-get-acad-object))
  (c:AUTOSTITCH)
  (ast:ui-adopt (ast:cad-read (car ast:demo:*guides*)))
  (ast:ui-status "Fourteen examples ready. The lower rows compare straight and curved junctions.")
  (vla-Save document)
  (princ))
(princ)
